module mef-sof-services {
  namespace "urn:mef:yang:mef-sof-services";
  prefix mef-services;

  import ietf-yang-types {
    prefix yang;
  }
  import mef-service-types {
    prefix mef-types;
  }
  import mef-sof-global {
    prefix mef-global;
  }
  import mef-sof-interfaces {
    prefix mef-interfaces;
  }

  organization "MEF Forum";
  contact
    "Web URL: http://mef.net/
     E-mail:  namespace@mef.net
     Postal:  MEFForum
              6033 W. Century Boulevard, Suite 1107
              Los Angeles, CA 90045
              U.S.A.
     Phone:   +1 310-642-2800
     Fax:     +1 310-642-2808";
  description
    "This module implements the Carrier Ethernet Services as 
     defined in MEF 10.3 and MEF 6.2.
     
     Reference Overview:
      A number of base documents have been used to create the 
      MEF Services YANG Module. The
      following are the abbreviations for the baseline documents:
      [RFC 6991] refers to IETF RFC 6991 'Common YANG Data Types',
      2013-07-15  
      [RFC 6643] refers to IETF RFC 6643 'Translation of Structure
      of Management Information
      Version 2 (SMIv2) MIB Modules to YANG Modules', 2011-11-25  
      [802.1AB] refers to 'Station and Media Access Control
      Connectivity Discovery', IEEE 802.1AB-2009, September 2009
      [802.1q] refers to IEEE 802.1Q-2011 'IEEE Standard for Local
      and metropolitan area networks --Media Access Control (MAC)
      Bridges and Virtual Bridged Local Area Networks, August 2011
      [802-2001] refers to 'IEEE Standard for Local and Metropolitan
      Area Networks: Overview and Architecture', IEEE 802-2001,
      February 2002
      [MEF10.3] refers to MEF 10.3 
      'Ethernet Services Attributes Phase 3', October 2013
      [MEF6.2] refers to MEF 6.2 
      'EVC Ethernet Services Defintions Phase 3', August 2014
      [MEF40] refers to MEF 40 
      'UNI and EVC Definition of Managed Objects', April 2013
      [MEF45] refers to MEF 45 'Multi-CEN L2CP', August 2014
      [MEF7.2] refers to MEF 7.2 
      'Carrier Ethernet Management Information Model', April 2013
      [MEF7.3] refers to MEF 7.3 
      'Carrier Ethernet Management Information Model',
      Working Draft #1 2015
      [RFC 2737] refers to IETF RFC 2737 'Entity MIB (Version 2)',
      December 1999
      [RFC 2863] refers to IETF RFC 2863 'The Interfaces Group MIB',
      June 2000
      [RFC 3419] refers to IETF RFC 3419 
      'Textual Conventions for Transport Addresses', December 2002
      [Y.1731] refers to ITU-T Y.1731 
      'OAM functions and mechanisms for Ethernet based networks',
      July 2011
      [Q.840.1] refers to ITU-T Q.840.1 
      'Requirements and analysis for NMS-EMS management interface
      of Ethernet over Transport and Metro Ethernet 
      Network(EoT/MEN)' March 2007";

  revision 2017-01-10 {
    description
      "Updated to address CFC1 Review Comments.";
    reference
      "EVC Ethernet Services Definitions YANG Modules 
       (MEF XX), TBD";
  }
  revision 2016-07-01 {
    description
      "Updated to better align with MEF 7.3 and
       MEF Common Information Model attributes";
    reference
      "EVC Ethernet Services Definitions YANG Modules 
       (MEF XX), TBD";
  }
  revision 2015-05-26 {
    description
      "Formal Project Review Draft 1.";
    reference "EVC Ethernet Services Definitions YANG Modules (MEF XX), TBD";
  }

  container mef-services {
    description
      "MEF Services Configuration and Status";
    container carrier-ethernet {
      description
        "MEF Services for Carrier EthernetConfiguration and Status";
      container subscriber-services {
        description
          "MEF Subscriber ServicesConfiguration and Status";
        list evc {
          key "evc-id";
          description
            "List of Ethernet Virtual Connection services (EVCs).";
          leaf evc-id {
            type mef-types:evc-id-type;
            description
              "An identifier for the EVC, that is unique across all the EVCs in the Service Provider's CEN";
            reference "[MEF10.3] Section 8.2 [R7]. [MEF7.3] Section 7.2.";
          }
          container cos-names {
            description
              "CoS Names (AKA CoS Labels) for use by this EVC.";
            list cos-name {
              key "name";
              description
                "List of CoS Names.";
              leaf name {
                type mef-types:identifier45;
                description
                  "CoS Name.";
              }
            }
          }
          container end-points {
            description
              "EVC End Point configuration and status. Note that EVC End Points contain the EVC per UNI attributes from MEF 10.3.";
            list end-point {
              must "not(ce-vlans/ce-vlan[2]) or ../../ce-vlan-id-preservation = 'true'" {
                error-message "When more than one CE-VLAN-ID is mapped to an EVC at a UNI, the EVC must have CE-VLAN ID Preservation Enabled.";
                description
                  "When more than one CE-VLAN-ID is mapped to an EVC at a UNI, the EVC must have CE-VLAN ID Preservation Enabled.";
                reference "[MEF10.3] [R25].";
              }
              must "(/mef-interfaces:mef-interfaces/mef-interfaces:unis/mef-interfaces:uni[mef-interfaces:uni-id = current()/mef-services:uni-id][mef-interfaces:uni-id/../mef-interfaces:bundling-enabled = 'true']) or (/mef-interfaces:mef-interfaces/mef-interfaces:unis/mef-interfaces:uni[mef-interfaces:uni-id = current()/mef-services:uni-id][mef-interfaces:uni-id/../mef-interfaces:all-to-one-bundling-enabled = 'true']) or not(ce-vlans/ce-vlan[2])" {
                error-message "If both Bundling and All-to-One Bundling are disabled for a UNI, only one CE VLAN ID can be configured for a specific EVC on that UNI.";
                description
                  "If both Bundling and All-to-One Bundling are disabled for a UNI, only one CE VLAN ID can be configured for a specific EVC on that UNI.";
                reference "[MEF10.3] [R77].";
              }
              must "(/mef-interfaces:mef-interfaces/mef-interfaces:unis/mef-interfaces:uni[mef-interfaces:uni-id = current()/mef-services:uni-id][mef-interfaces:uni-id/../mef-interfaces:all-to-one-bundling-enabled = 'false']) or ((count(/mef-services:mef-services/carrier-ethernet/subscriber-services/evc/end-points/end-point[uni-id = current()/uni-id]) = 1) and (count(/mef-interfaces:mef-interfaces/mef-interfaces:unis/mef-interfaces:uni[mef-interfaces:uni-id = current()/mef-services:uni-id]/mef-interfaces:ce-vlans/mef-interfaces:ce-vlan[not(mef-interfaces:vid = current()/mef-services:ce-vlans/mef-services:ce-vlan/mef-services:vid)]) = 0))" {
                error-message "If All-to-One Bundling is enabled for any UNI in an EVC, all CE-VLAN IDs for that UNI must map to a single EVC.";
                description
                  "If All-to-One Bundling is enabled for any UNI in an EVC, all CE-VLAN IDs for that UNI must map to a single EVC.";
                reference "[MEF10.3] [R82].";
              }
              must "((/mef-interfaces:mef-interfaces/mef-interfaces:unis/mef-interfaces:uni[mef-interfaces:uni-id = current()/mef-services:uni-id][mef-interfaces:uni-id/../mef-interfaces:ingress-bw-profile-per-uni]) or (/mef-services:mef-services/carrier-ethernet/subscriber-services/evc/end-points/end-point[uni-id = current()/mef-services:uni-id]/ingress-bwp-flows-per-cos) or (/mef-services:mef-services/carrier-ethernet/subscriber-services/evc/end-points/end-point[uni-id = current()/mef-services:uni-id]/ingress-bw-profile-per-evc)) or not(/mef-interfaces:mef-interfaces/mef-interfaces:unis/mef-interfaces:uni[mef-interfaces:uni-id = current()/mef-services:uni-id]/mef-interfaces:ingress-envelopes)" {
                error-message "If no Ingress Bandwidth Profiles are specified for this UNI (BW Profile Per UNI, BWP Flows Per CoS, nor BW Profile Per EVC), then the UNI Ingress Envelopes list must be empty.";
                description
                  "If no Ingress Bandwidth Profiles are specified for this UNI (BW Profile Per UNI, BWP Flows Per CoS, nor BW Profile Per EVC), then the UNI Ingress Envelopes list must be empty.";
                reference "MEF 6.2 [R4].";
              }
              must "((/mef-interfaces:mef-interfaces/mef-interfaces:unis/mef-interfaces:uni[mef-interfaces:uni-id = current()/mef-services:uni-id][mef-interfaces:uni-id/../mef-interfaces:egress-bw-profile-per-uni]) or (/mef-services:mef-services/carrier-ethernet/subscriber-services/evc/end-points/end-point[uni-id = current()/mef-services:uni-id]/egress-bwp-flows-per-eec) or (/mef-services:mef-services/carrier-ethernet/subscriber-services/evc/end-points/end-point[uni-id = current()/mef-services:uni-id]/egress-bw-profile-per-evc)) or not(/mef-interfaces:mef-interfaces/mef-interfaces:unis/mef-interfaces:uni[mef-interfaces:uni-id = current()/mef-services:uni-id]/mef-interfaces:egress-envelopes)" {
                error-message "If no Egress Bandwidth Profiles are specied for this UNI (BW Profile Per UNI, BWP Flows Per EEC, nor BW Profile Per EVC), then the UNI Egress Envelopes list must be empty.";
                description
                  "If no Egress Bandwidth Profiles are specied for this UNI (BW Profile Per UNI, BWP Flows Per EEC, nor BW Profile Per EVC), then the UNI Egress Envelopes list must be empty.";
                reference "[MEF10.3] [R4].";
              }
              key "uni-id";
              description
                "List of EVC End Points for the EVC. Each EVC End Point in the EVC is associated with a distinct UNI, and contains the EVC per UNI attributes described in MEF 10.3.";
              reference "[MEF10.3] Section 8.3, Section 9.10, and Section 10. [MEF7.3] Section 7.4 and Section 7.5.";
              container ce-vlans {
                description
                  "Container for the list of CE-VLAN IDs that map to this EVC End Point.";
                list ce-vlan {
                  key "vid";
                  min-elements "1";
                  description
                    "The list of CE-VLAN IDs that map to this EVC End Point - that is, that map to this EVC at the associated UNI.";
                  reference "[MEF10.3] Section 9.10. [MEF7.3] Section 7.5.";
                  leaf vid {
                    type leafref {
                      path "/mef-interfaces:mef-interfaces/mef-interfaces:unis/mef-interfaces:uni[mef-interfaces:uni-id = current()/../../../uni-id]/mef-interfaces:ce-vlans/mef-interfaces:ce-vlan/mef-interfaces:vid";
                    }
                    must "not(current()/../../ce-vlan[2]) or (count(../../../../end-point/ce-vlans/ce-vlan[vid = current()]) = count(../../../../end-point))" {
                      error-message "If more than one CE-VLAN ID is configured for a UNI as part of an EVC, every CE VLAN-ID mapped to that EVC must be configured for all UNIs within that EVC.";
                      description
                        "If more than one CE-VLAN ID is configured for a UNI as part of an EVC, every CE VLAN-ID mapped to that EVC must be configured for all UNIs within that EVC.";
                      reference "[MEF10.3] [R81].";
                    }
                    must "count(/mef-services:mef-services/carrier-ethernet/subscriber-services/evc/end-points/end-point[uni-id = current()/../../../uni-id]/mef-services:ce-vlans/mef-services:ce-vlan[mef-services:vid = current()]) = 1" {
                      error-message "At each UNI there MUST be a mapping of each CE-VLAN ID to at most one EVC.";
                      description
                        "At each UNI there MUST be a mapping of each CE-VLAN ID to at most one EVC.";
                      reference "[MEF10.3] [R76].";
                    }
                    description
                      "CE-VLAN Identifier that maps to this EVC End Point.";
                  }
                }
              }
              choice ingress-bwp-choices {
                description
                  "Choice to ensure one cannot configure BWP per-cos and per-evc at the same time.";
                case ingress-bwp-per-cos-option {
                  container ingress-bwp-flows-per-cos {
                    description
                      "The EVC Ingress Bandwidth Profile Flows per UNI Class of Service Identifiers";
                    leaf coupling-enabled {
                      type boolean;
                      default "false";
                      description
                        "EVC Per UNI Envelope Coupling Flag (CF) attribute.";
                      reference "[MEF10.3] Section 12.1.";
                    }
                    list bwp-flow-per-cos {
                      key "cos-name";
                      description
                        "EVC Per UNI: The list of Class of Service Identifiers corresponding to this UNI's Ingress Bandwidth Profile Flow.";
                      leaf cos-name {
                        type leafref {
                          path "../../../../../cos-names/cos-name/name";
                        }
                        description
                          "EVC Per UNI: Class of Service Identifier for this Bandwidth Profile Flow.";
                        reference "[MEF7.3] Section 12.1.2.";
                      }
                      leaf envelope-id {
                        type leafref {
                          path "/mef-interfaces:mef-interfaces/mef-interfaces:unis/mef-interfaces:uni[mef-interfaces:uni-id = current()/../../../uni-id]/mef-interfaces:ingress-envelopes/mef-interfaces:envelope/mef-interfaces:envelope-id";
                        }
                        must "count(/mef-services:mef-services/carrier-ethernet/subscriber-services/evc/end-points/end-point[uni-id = current()/../../../uni-id][./ingress-bw-profile-per-evc/envelope-id = current()]) = 0" {
                          error-message "All EVCs sharing a Ingress Bandwidth Profile Envelope for a UNI must use the same BWP Method ( Per-EVC or Per-CoS).";
                          description
                            "All EVCs sharing a Ingress Bandwidth Profile Envelope for a UNI must use the same BWP Method ( Per-EVC or Per-CoS).";
                          reference "[MEF10.3] [R135].";
                        }
                        mandatory true;
                        description
                          "EVC Per UNI: Ingress Bandwidth Profile Envelope Per CoS ID. If this parameter is not configured (ie. 'No') this setting is configured else at the UNI Level.";
                        reference "[MEF10.3] Section 10.6, Table 28. [MEF7.3] Section 12.1.2.";
                      }
                      leaf bw-profile {
                        type leafref {
                          path "/mef-interfaces:mef-interfaces/mef-interfaces:unis/mef-interfaces:uni[mef-interfaces:uni-id = current()/../../../uni-id]/mef-interfaces:ingress-envelopes/mef-interfaces:envelope[mef-interfaces:envelope-id = current()/../envelope-id]/mef-interfaces:bwp-flows/mef-interfaces:bwp-flow/mef-interfaces:bw-profile";
                        }
                        mandatory true;
                        description
                          "EVC Per UNI: Ingress Bandwidth Profile Envelope Per CoS ID. If this parameter is not configured (ie. 'No') this setting is configured else at the UNI Level.";
                        reference "[MEF10.3] Section 10.6, Table 28. [MEF7.3] Section 12.1.2.";
                      }
                    }
                  }
                }
                case ingress-per-evc-option{
                  container ingress-bw-profile-per-evc {
                    leaf envelope-id {
                      type leafref {
                        path "/mef-interfaces:mef-interfaces/mef-interfaces:unis/mef-interfaces:uni[mef-interfaces:uni-id = current()/../../uni-id]/mef-interfaces:ingress-envelopes/mef-interfaces:envelope/mef-interfaces:envelope-id";
                      }
                      must "count(/mef-services:mef-services/carrier-ethernet/subscriber-services/evc/end-points/end-point[uni-id = current()/../../uni-id]/ingress-bwp-flows-per-cos/bwp-flow-per-cos/envelope-id = current()) = 0" {
                        error-message "All EVCs sharing a Ingress Bandwidth Profile Envelope for a UNI must use the same BWP Method (Per-CoS or Per-EVC).";
                        description
                          "All EVCs sharing a Ingress Bandwidth Profile Envelope for a UNI must use the same BWP Method (Per-CoS or Per-EVC).";
                        reference "[MEF10.3] [R135].";
                      }
                      description
                        "EVC Per UNI: Ingress Bandwidth Profile Per EVC. If this parameter is not configured, there is no ingress Bandwidth Profile per EVC.";
                      reference "[MEF10.3] Section 10.5. [MEF7.3] Section 12.1.2.";
                    }
                    leaf bw-profile {
                      type leafref {
                        path "/mef-interfaces:mef-interfaces/mef-interfaces:unis/mef-interfaces:uni[mef-interfaces:uni-id = current()/../../uni-id]/mef-interfaces:ingress-envelopes/mef-interfaces:envelope[mef-interfaces:envelope-id = current()/../envelope-id]/mef-interfaces:bwp-flows/mef-interfaces:bwp-flow/mef-interfaces:bw-profile";
                      }
                      mandatory true;
                      description
                        "EVC Per UNI: Ingress Bandwidth Profile Envelope Per CoS ID. If this parameter is not configured (ie. 'No') this setting is configured else at the UNI Level.";
                      reference "[MEF10.3] Section 10.6, Table 28. [MEF7.3] Section 12.1.2.";
                    }
                    description
                      "EVC Per UNI: Ingress Bandwidth Profile Per EVC.";
                  }
                }
              }
              choice egress-bwp-choices {
                description
                  "Choice to ensure one cannot configure BWP per-cos and per-evc at the same time.";
                case egress-bwp-per-cos-option {
                  container egress-bwp-flows-per-eec {
                    description
                      "EVC Per UNI: The Egress Equivalence Class Identifiers corresponding to this EVC's Egress Bandwidth Profile Flows.";
                    leaf coupling-enabled {
                      type boolean;
                      default "false";
                      description
                        "EVC Per UNI: The Envelope Coupling Flag (CF) attribute.";
                      reference "[MEF10.3] Section 12.1.";
                    }
                    list bwp-flow-per-eec {
                      key "eec-name";
                      description
                        "EVC Per UNI: The list of Egress Equivalence Class Identifiers corresponding to this EVC's Egress Bandwidth Profile Flow.";
                      leaf eec-name {
                        type leafref {
                          path "../../../../../cos-names/cos-name/name";
                        }
                        description
                          "EVC Per UNI: Egress Equivalence Class Identifier for this Bandwidth Profile Flow.";
                        reference "[MEF7.3] Section 12.1.2.";
                      }
                      leaf envelope-id {
                        type leafref {
                          path "/mef-interfaces:mef-interfaces/mef-interfaces:unis/mef-interfaces:uni[mef-interfaces:uni-id = current()/../../../uni-id]/mef-interfaces:egress-envelopes/mef-interfaces:envelope/mef-interfaces:envelope-id";
                        }
                        must "count(/mef-services:mef-services/carrier-ethernet/subscriber-services/evc/end-points/end-point[uni-id = current()/../../../uni-id][./egress-bw-profile-per-evc/envelope-id = current()]) = 0" {
                          error-message "All EVCs sharing a Egress Bandwidth Profile Envelope for a UNI must use the same BWP Method ( Per-EVC or Per-CoS).";
                          description
                            "All EVCs sharing a Egress Bandwidth Profile Envelope for a UNI must use the same BWP Method ( Per-EVC or Per-CoS).";
                          reference "[MEF10.3] [R135].";
                        }
                        mandatory true;
                        description
                          "EVC Per UNI: Egress Bandwidth Profile Envelope Per Equivance Class. If this parameter is not configured (ie. 'No') this setting is configured else at the UNI Level.";
                        reference "[MEF10.3] Section 10.6, Table 28. [MEF7.3] Section 12.1.2.";
                      }
                      leaf bw-profile {
                        type leafref {
                          path "/mef-interfaces:mef-interfaces/mef-interfaces:unis/mef-interfaces:uni[mef-interfaces:uni-id = current()/../../../uni-id]/mef-interfaces:egress-envelopes/mef-interfaces:envelope[mef-interfaces:envelope-id = current()/../envelope-id]/mef-interfaces:bwp-flows/mef-interfaces:bwp-flow/mef-interfaces:bw-profile";
                        }
                        mandatory true;
                        description
                          "EVC Per UNI: Egress Bandwidth Profile Envelope Per Equivance Class. If this parameter is not configured (ie. 'No') this setting is configured else at the UNI Level.";
                        reference "[MEF10.3] Section 10.6, Table 28. [MEF7.3] Section 12.1.2.";
                      }
                    }
                  }
                }
                case egress-per-evc-option {
                  container egress-bw-profile-per-evc {
                    leaf envelope-id {
                      type leafref {
                        path "/mef-interfaces:mef-interfaces/mef-interfaces:unis/mef-interfaces:uni[mef-interfaces:uni-id = current()/../../uni-id]/mef-interfaces:egress-envelopes/mef-interfaces:envelope/mef-interfaces:envelope-id";
                      }
                      must "count(/mef-services:mef-services/carrier-ethernet/subscriber-services/evc/end-points/end-point[uni-id = current()/../../uni-id][./egress-bwp-flows-per-eec/bwp-flow-per-eec/envelope-id = current()]) = 0" {
                        error-message "All EVCs sharing a Egress Bandwidth Profile Envelope for a UNI must use the same BWP Method (Per-CoS or Per-EVC).";
                        description
                          "All EVCs sharing a Egress Bandwidth Profile Envelope for a UNI must use the same BWP Method (Per-CoS or Per-EVC).";
                        reference "[MEF10.3] [R135].";
                      }
                      description
                        "EVC Per UNI: Egress Bandwidth Profile Per EVC. If this parameter is not configured, there is no egress Bandwidth Profile per EVC.";
                      reference "[MEF10.3] Section 10.7. [MEF7.3] Section 12.1.2.";
                    }
                    leaf bw-profile {
                      type leafref {
                        path "/mef-interfaces:mef-interfaces/mef-interfaces:unis/mef-interfaces:uni[mef-interfaces:uni-id = current()/../../uni-id]/mef-interfaces:egress-envelopes/mef-interfaces:envelope[mef-interfaces:envelope-id = current()/../envelope-id]/mef-interfaces:bwp-flows/mef-interfaces:bwp-flow/mef-interfaces:bw-profile";
                      }
                      mandatory true;
                      description
                        "EVC Per UNI: Egress Bandwidth Profile Envelope Per Equivance Class. If this parameter is not configured (ie. 'No') this setting is configured else at the UNI Level.";
                      reference "[MEF10.3] Section 10.6, Table 28. [MEF7.3] Section 12.1.2.";
                    }
                    description
                      "Egress Bandwidth Profile Per EVC";
                  }
                }
              }
              container status {
                description
                  "EVC Per UNI: This status group is related to the MEF 7.3 Service Endpoint";
                leaf operational-state {
                  type boolean;
                  default "false";
                  config false;
                  description
                    "EVC Per UNI: Operational Status of the EVC, which is either Enabled (if the value is true) or Disabled (if the value is false).";
                  reference "[MEF15]. [MEF7.3] Section 7.4.";
                }
                leaf evc-end-point-id {
                  type mef-types:identifier90;
                  config false;
                  description
                    "EVC Per UNI: This is 90 character long string (max) containing the concatenation of the evc-id and uni-id keys for this end-point";
                  reference "[MEF7.3] Section 7.5";
                }
              }
              leaf uni-id {
                type leafref {
                  path "/mef-interfaces:mef-interfaces/mef-interfaces:unis/mef-interfaces:uni/mef-interfaces:uni-id";
                }
                description
                  "EVC Per UNI: UNI ID of the UNI where this EVC End Point is located.";
                reference "[MEF10.3] Section 8.3, Section 10.1.  [MEF7.3] Section 7.5.";
              }
              leaf role {
                type mef-types:evc-uni-role-type;
                mandatory true;
                description
                  "EVC Per UNI: The UNI Role MUST have the value of either 'root' or 'leaf'. A root role UNI may be connected to multiple other UNI in the EVC while a leaf role UNI may only connect to one other UNI.";
                reference "[MEF10.3] Section 8.3. [MEF7.3] Section 7.5.";
              }
              leaf admin-state {
                type boolean;
                default "true";
                description
                  "EVC Per UNI: Indicates whether the EVC End Point is adminstratively locked (if the value is false) or unlocked (if the value if true).";
                reference "[MEF7.3] Section 7.4.";
              }
              leaf color-identifier {
                type mef-types:evc-color-identifier-type;
                description
                  "EVC Per UNI: The Color Identifier for Service Frames.";
                reference "[MEF10.3] Section 10.3. [MEF7.3] Section 7.4 and Section 7.13.";
              }
              leaf cos-identifier {
                type leafref {
                  path "/mef-global:mef-global/mef-global:profiles/mef-global:cos/mef-global:cos-profile/mef-global:id";
                }
                must "not(/mef-global:mef-global/mef-global:profiles/mef-global:cos/mef-global:cos-profile[mef-global:id = current()]/mef-global:cos-pcp) or count(/mef-global:mef-global/mef-global:profiles/mef-global:cos/mef-global:cos-profile[mef-global:id = current()]/mef-global:cos-pcp/mef-global:pcp[not(mef-global:cos-name = current()/../../../cos-names/cos-name/name)]) = 0" {
                  error-message "When the Class of Service Identifier is based on PCP for a given EVC at a given UNI, all cos-pcp CoS Names must be in the the EVC Cos Names List.";
                  description
                    "When the Class of Service Identifier is based on PCP for a given EVC at a given UNI, all cos-pcp CoS Names must be in the the EVC Cos Names List.";
                  reference "[MEF10.3] [R135].";
                }
                must "not(/mef-global:mef-global/mef-global:profiles/mef-global:cos/mef-global:cos-profile[mef-global:id = current()]/mef-global:cos-dscp) or count(/mef-global:mef-global/mef-global:profiles/mef-global:cos/mef-global:cos-profile[mef-global:id = current()]/mef-global:cos-dscp/mef-global:ipv4-dscp[not(mef-global:cos-name = current()/../../../cos-names/cos-name/name)]) = 0" {
                  error-message "When the Class of Service Identifier is based on DSCP for a given EVC at a given UNI, all IPv4 cos-dscp CoS Names must be in the the EVC Cos Names List.";
                  description
                    "When the Class of Service Identifier is based on DSCP for a given EVC at a given UNI, all IPv4 cos-dscp CoS Names must be in the the EVC Cos Names List.";
                  reference "[MEF10.3] [R135].";
                }
                must "not(/mef-global:mef-global/mef-global:profiles/mef-global:cos/mef-global:cos-profile[mef-global:id = current()]/mef-global:cos-dscp) or count(/mef-global:mef-global/mef-global:profiles/mef-global:cos/mef-global:cos-profile[mef-global:id = current()]/mef-global:cos-dscp/mef-global:ipv6-dscp[not(mef-global:cos-name = current()/../../../cos-names/cos-name/name)]) = 0" {
                  error-message "When the Class of Service Identifier is based on DSCP for a given EVC at a given UNI, all IPv6 cos-dscp CoS Names must be in the the EVC Cos Names List.";
                  description
                    "When the Class of Service Identifier is based on DSCP for a given EVC at a given UNI, all IPv6 cos-dscp CoS Names must be in the the EVC Cos Names List.";
                  reference "[MEF10.3] [R135].";
                }
                must "not(/mef-global:mef-global/mef-global:profiles/mef-global:cos/mef-global:cos-profile[mef-global:id = current()]/mef-global:cos-pcp) or (../../../cos-names/cos-name[name = /mef-global:mef-global/mef-global:profiles/mef-global:cos/mef-global:cos-profile[mef-global:id = current()]/mef-global:cos-pcp/mef-global:default-pcp-cos-name])" {
                  error-message "When the Class of Service Identifier is based on PCP for a given EVC at a given UNI, the default-pcp-cos-name must be in the the EVC Cos Names List.";
                  description
                    "When the Class of Service Identifier is based on PCP for a given EVC at a given UNI, the default-pcp-cos-name must be in the the EVC Cos Names List.";
                  reference "[MEF10.3] [R135].";
                }
                must "not(/mef-global:mef-global/mef-global:profiles/mef-global:cos/mef-global:cos-profile[mef-global:id = current()]/mef-global:cos-evc) or (../../../cos-names/cos-name[name = /mef-global:mef-global/mef-global:profiles/mef-global:cos/mef-global:cos-profile[mef-global:id = current()]/mef-global:cos-evc/mef-global:default-evc-cos-name])" {
                  error-message "When the Class of Service Identifier is based on EVC for a given EVC at a given UNI, the default-evc-cos-name must be in the the EVC Cos Names List.";
                  description
                    "When the Class of Service Identifier is based on EVC for a given EVC at a given UNI, the default-evc-cos-name must be in the the EVC Cos Names List.";
                  reference "[MEF10.3] [R135].";
                }
                must "not(/mef-global:mef-global/mef-global:profiles/mef-global:cos/mef-global:cos-profile[mef-global:id = current()]/mef-global:cos-dscp) or (../../../cos-names/cos-name[name = /mef-global:mef-global/mef-global:profiles/mef-global:cos/mef-global:cos-profile[mef-global:id = current()]/mef-global:cos-dscp/mef-global:default-ipv4-cos-name])" {
                  error-message "When the Class of Service Identifier is based on DSCP for a given EVC at a given UNI, the default-ipv4-cos-name must be in the the EVC Cos Names List.";
                  description
                    "When the Class of Service Identifier is based on DSCP for a given EVC at a given UNI, the default-ipv4-cos-name must be in the the EVC Cos Names List.";
                  reference "[MEF10.3] [R135].";
                }
                must "not(/mef-global:mef-global/mef-global:profiles/mef-global:cos/mef-global:cos-profile[mef-global:id = current()]/mef-global:cos-dscp) or (../../../cos-names/cos-name[name = /mef-global:mef-global/mef-global:profiles/mef-global:cos/mef-global:cos-profile[mef-global:id = current()]/mef-global:cos-dscp/mef-global:default-ipv6-cos-name])" {
                  error-message "When the Class of Service Identifier is based on DSCP for a given EVC at a given UNI, the default-ipv6-cos-name must be in the the EVC Cos Names List.";
                  description
                    "When the Class of Service Identifier is based on DSCP for a given EVC at a given UNI, the default-ipv6-cos-name must be in the the EVC Cos Names List.";
                  reference "[MEF10.3] [R135].";
                }
                must "not(/mef-global:mef-global/mef-global:profiles/mef-global:cos/mef-global:cos-profile[mef-global:id = current()]/mef-global:cos-pcp) or ((/mef-global:mef-global/mef-global:profiles/mef-global:cos/mef-global:cos-profile[mef-global:id = current()]/mef-global:cos-pcp) and ((../color-identifier = 'pcp') or (../color-identifier = 'dei')) )" {
                  error-message "When the Class of Service Identifier is based on PCP for a given EVC at a given UNI, the Color Identifier must be based on either DEI or PCP.";
                  description
                    "When the Class of Service Identifier is based on PCP for a given EVC at a given UNI, the Color Identifier must be based on either DEI or PCP.";
                  reference "[MEF10.3] [R111].";
                }
                must "not(/mef-global:mef-global/mef-global:profiles/mef-global:cos/mef-global:cos-profile[mef-global:id = current()]/mef-global:cos-dscp) or ((/mef-global:mef-global/mef-global:profiles/mef-global:cos/mef-global:cos-profile[mef-global:id = current()]/mef-global:cos-dscp) and (../color-identifier = 'dscp'))" {
                  error-message "When the Class of Service Identifier is based on DSCP for a given EVC at a given UNI, the Color Identifier must be based DSCP.";
                  description
                    "When the Class of Service Identifier is based on DSCP for a given EVC at a given UNI, the Color Identifier must be based DSCP.";
                  reference "[MEF10.3] [R112].";
                }
                mandatory true;
                description
                  "EVC Per UNI: Reference to a global CoS Profile that specifies how to assign CoS Names to ingress frames at this EVC End Point based on fields in the frame.";
                reference "[MEF10.3] Section 10.2. [MEF7.3] Section 7.11.";
              }
              leaf eec-identifier {
                type leafref {
                  path "/mef-global:mef-global/mef-global:profiles/mef-global:eec/mef-global:eec-profile/mef-global:id";
                }
                must "not(/mef-global:mef-global/mef-global:profiles/mef-global:eec/mef-global:eec-profile[mef-global:id = current()]/mef-global:eec-pcp) or count(/mef-global:mef-global/mef-global:profiles/mef-global:eec/mef-global:eec-profile[mef-global:id = current()]/mef-global:eec-pcp/mef-global:pcp[not(mef-global:eec-name = current()/../../../cos-names/cos-name/name)]) = 0" {
                  error-message "When the EEC Identifier is based on PCP for a given EVC at a given UNI, all eec-pcp CoS Names must be in the the EVC Cos Names List.";
                  description
                    "When the EEC Identifier is based on PCP for a given EVC at a given UNI, all eec-pcp CoS Names must be in the the EVC Cos Names List.";
                  reference "[MEF10.3] [R135].";
                }
                must "not(/mef-global:mef-global/mef-global:profiles/mef-global:eec/mef-global:eec-profile[mef-global:id = current()]/mef-global:eec-dscp) or count(/mef-global:mef-global/mef-global:profiles/mef-global:eec/mef-global:eec-profile[mef-global:id = current()]/mef-global:eec-dscp/mef-global:ipv4-dscp[not(mef-global:eec-name = current()/../../../cos-names/cos-name/name)]) = 0" {
                  error-message "When the EEC Identifier is based on DSCP for a given EVC at a given UNI, all IPv4 eec-dscp CoS Names must be in the the EVC Cos Names List.";
                  description
                    "When the EEC Identifier is based on DSCP for a given EVC at a given UNI, all IPv4 eec-dscp CoS Names must be in the the EVC Cos Names List.";
                  reference "[MEF10.3] [R135].";
                }
                must "not(/mef-global:mef-global/mef-global:profiles/mef-global:eec/mef-global:eec-profile[mef-global:id = current()]/mef-global:eec-dscp) or count(/mef-global:mef-global/mef-global:profiles/mef-global:eec/mef-global:eec-profile[mef-global:id = current()]/mef-global:eec-dscp/mef-global:ipv6-dscp[not(mef-global:eec-name = current()/../../../cos-names/cos-name/name)]) = 0" {
                  error-message "When the EEC Identifier is based on DSCP for a given EVC at a given UNI, all IPv6 eec-dscp CoS Names must be in the the EVC Cos Names List.";
                  description
                    "When the EEC Identifier is based on DSCP for a given EVC at a given UNI, all IPv6 eec-dscp CoS Names must be in the the EVC Cos Names List.";
                }
                must "not(/mef-global:mef-global/mef-global:profiles/mef-global:eec/mef-global:eec-profile[mef-global:id = current()]/mef-global:eec-pcp) or (../../../cos-names/cos-name[name = /mef-global:mef-global/mef-global:profiles/mef-global:eec/mef-global:eec-profile[mef-global:id = current()]/mef-global:eec-pcp/mef-global:default-pcp-eec-name])" {
                  error-message "When the EEC Identifier is based on PCP for a given EVC at a given UNI, the default-pcp-eec-name must be in the the EVC Cos Names List.";
                  description
                    "When the EEC Identifier is based on PCP for a given EVC at a given UNI, the default-pcp-eec-name must be in the the EVC Cos Names List.";
                  reference "[MEF10.3] [R135].";
                }
                must "not(/mef-global:mef-global/mef-global:profiles/mef-global:eec/mef-global:eec-profile[mef-global:id = current()]/mef-global:eec-dscp) or (../../../cos-names/cos-name[name = /mef-global:mef-global/mef-global:profiles/mef-global:eec/mef-global:eec-profile[mef-global:id = current()]/mef-global:eec-dscp/mef-global:default-ipv4-eec-name])" {
                  error-message "When the EEC Identifier is based on DSCP for a given EVC at a given UNI, the default-ipv4-eec-name must be in the the EVC Cos Names List.";
                  description
                    "When the EEC Identifier is based on DSCP for a given EVC at a given UNI, the default-ipv4-eec-name must be in the the EVC Cos Names List.";
                  reference "[MEF10.3] [R135].";
                }
                must "not(/mef-global:mef-global/mef-global:profiles/mef-global:eec/mef-global:eec-profile[mef-global:id = current()]/mef-global:eec-dscp) or (../../../cos-names/cos-name[name = /mef-global:mef-global/mef-global:profiles/mef-global:eec/mef-global:eec-profile[mef-global:id = current()]/mef-global:eec-dscp/mef-global:default-ipv6-eec-name])" {
                  error-message "When the EEC Identifier is based on DSCP for a given EVC at a given UNI, the default-ipv6-eec-name must be in the the EVC Cos Names List.";
                  description
                    "When the EEC Identifier is based on DSCP for a given EVC at a given UNI, the default-ipv6-eec-name must be in the the EVC Cos Names List.";
                  reference "[MEF10.3] [R135].";
                }
                must "not(/mef-global:mef-global/mef-global:profiles/mef-global:eec/mef-global:eec-profile[mef-global:id = current()]/mef-global:eec-pcp) or ((/mef-global:mef-global/mef-global:profiles/mef-global:eec/mef-global:eec-profile[mef-global:id = current()]/mef-global:eec-pcp) and ((../color-identifier = 'pcp') or (../color-identifier = 'dei')) )" {
                  error-message "When the Egress Equivalence Class Identifier is based on PCP for a given EVC at a given UNI, the Color Identifier must be based on either DEI or PCP.";
                  description
                    "When the Egress Equivalence Class Identifier is based on PCP for a given EVC at a given UNI, the Color Identifier must be based on either DEI or PCP.";
                  reference "[MEF10.3] [R111].";
                }
                must "not(/mef-global:mef-global/mef-global:profiles/mef-global:eec/mef-global:eec-profile[mef-global:id = current()]/mef-global:eec-dscp) or ((/mef-global:mef-global/mef-global:profiles/mef-global:eec/mef-global:eec-profile[mef-global:id = current()]/mef-global:eec-dscp) and (../color-identifier = 'dscp'))" {
                  error-message "When the Egress Equivalence Class Identifier is based on DSCP for a given EVC at a given UNI, the Color Identifier must be based DSCP.";
                  description
                    "When the Egress Equivalence Class Identifier is based on DSCP for a given EVC at a given UNI, the Color Identifier must be based DSCP.";
                  reference "[MEF10.3] [R112].";
                }
                mandatory true;
                description
                  "EVC Per UNI: Reference to a global EEC Profile that specifies how to assign EEC Names to egress frames at this EVC End Point based on fields in the frame.";
                reference "[MEF10.3] Section 10.4. [MEF7.3] Section 7.11.";
              }
              leaf source-mac-address-limit {
                type uint32 {
                  range "1..max";
                }
                description
                  "EVC Per UNI: Source MAC Address Limit.";
                reference "[MEF10.3] Section 10.9. [MEF7.3] Section 7.4.";
              }
              leaf source-mac-address-limit-time-interval {
                when "../source-mac-address-limit";
                type yang:timeticks;
                default "0";
                description
                  "EVC Per UNI: Source MAC Address Limit Interval. This value is used when the Source MAC Address Limit has been configured.";
                reference "[MEF10.3] Section 10.9. [MEF7.3] Section 8.1.13.";
              }
              leaf test-meg-enabled {
                type boolean;
                default "false";
                description
                  "EVC Per UNI: Test MEG Enabled / Disabled.";
                reference "[MEF10.3] Section 10.10. [MEF7.3] Section 7.5.";
              }
              leaf user-label {
                type mef-types:identifier1023;
                description
                  "EVC Per UNI: User Label.";
                reference "[MEF7.3] Section 7.5.";
              }
              leaf subscriber-meg-mip-enabled {
                type boolean;
                default "false";
                description
                  "EVC Per UNI: Subscriber MEG MIP Enabled / Disabled.";
                reference "[MEF10.3] Section 10.11. [MEF7.3] Section 7.5";
              }
            }
          }
          container status {
            description
              "This status group is related to the MEF 7.3 Virtual Connection";
            leaf operational-state {
              type boolean;
              default "false";
              config false;
              description
                "EVC Operational Status: The value is either Enabled (if the value is 'true') or Disabled (if the value is 'false').";
              reference "[MEF7.3] Section 7.1.";
            }
            leaf service-state {
              type mef-types:service-state-type;
              default "pending";
              config false;
              description
                "EVC Service State.";
              reference "[MEF7.3] Section 7.1.";
            }
          }
          container carrier-ethernet-sls {
            description
              "Carrier Ethernet Service Level Specification";
            leaf sls-id {
              type leafref {
                path "/mef-global:mef-global/mef-global:sls-profiles/mef-global:sls-profile/mef-global:sls-id";
              }
              description
                "EVC: EVC-specific performance objectives and parameters. Note that an SLS can also specify performance objectives spanning more than one EVC. By default, all the UNI associated with the EVC have this SLS applied for them.";
              reference "[MEF10.3] Section 8.8, Section 10. [MEF7.3] Section 12.2.2.";
            }
            leaf start-time {
              type yang:date-and-time;
              mandatory true;
              description
                "Performance Metric(PM): Start DateTime for Time Intervals using a RFC 3339 formatted string (YYYY-MM-DDTHH:MM:SS[+HH:MM]). The timezone offset is optional but will be assumed as [+00:00].";
            }
            container cos-entries {
              description
                "SLS Inclusions by CoS: For this EVC, the following CoS Names/Labels are applicable.";
              list cos-entry {
                key "cos-name";
                description
                  "CoS Name.";
                leaf cos-name {
                  type leafref {
                    path "../../../../cos-names/cos-name/name";
                  }
                  description
                    "EVC: This attribute identifies the name of a class of service (CoS) instance to be used for EVC Performance.";
                }
                container pm-entries {
                  description
                    "Performance Metrics List";
                  list pm-entry {
                    key "pm-entry-id";
                    description
                      "Performance Metric Groups";
                    leaf pm-entry-id {
                      type leafref {
                        path "/mef-global:mef-global/mef-global:sls-profiles/mef-global:sls-profile[mef-global:sls-id = current()/../../../../../sls-id]/mef-global:pm-cos-name-entries/mef-global:pm-cos-name-entry[mef-global:cos-name = current()/../../../cos-name]/mef-global:pm-entries/mef-global:pm-entry/mef-global:pm-entry-id";
                      }
                      description
                        "Performance Metric Group Identifier";
                    }
                    container sets-of-end-point-pairs {
                      when "(/mef-global:mef-global/mef-global:sls-profiles/mef-global:sls-profile[mef-global:sls-id = current()/../../../../../sls-id]/mef-global:pm-cos-name-entries/mef-global:pm-cos-name-entry[mef-global:cos-name = current()/../../../cos-name]/mef-global:pm-entries/mef-global:pm-entry[mef-global:pm-entry-id = current()/../pm-entry-id]/mef-global:one-way-group-availability-pm)" {
                        description
                          "Only visible when one-way-group-availability-pm is being configured.";
                      }
                      description
                        "Set of End Point Pairs";
                      list set-of-end-point-pairs {
                        must "not(sls-uni-inclusions) or (sls-uni-inclusions and not(sls-uni-exclusions))" {
                          error-message "The EVC Performance SLS Exclusions and Inclusions List cannot both be configured for an EVC.";
                          description
                            "The EVC Performance SLS Exclusions and Inclusions List cannot both be configured for an EVC.";
                          reference "[MEF10.3] [R32].";
                        }
                        must "(../../../../../../../connection-type != 'rooted-multipoint') or ((../../../../../../../connection-type = 'rooted-multipoint') and not(sls-uni-exclusions) )" {
                          error-message "If EVC Type is Rooted-Multipoint, sls-uni-inclusions must be used instead of sls-uni-exclusions.";
                          description
                            "If EVC Type is Rooted-Multipoint, sls-uni-inclusions must be used instead of sls-uni-exclusions.";
                          reference "[MEF10.3].";
                        }
                        key "index";
                        description
                          "Set of End Point Pairs";
                        leaf index {
                          type uint32;
                          description
                            "An index value to identify this set of end-point pairs";
                        }
                        container sls-uni-inclusions {
                          presence "EVC: Defines the EVC End Points (UNI) Pairs that must conform to the EVC's SLS Performance Metrics.";
                          description
                            "SLS UNI Inclusions List. The following pairs of UNI Interconnections are to required to meet the SLS Performance Objectives. Configing both SLS UNI Inclusions and SLS UNI Exclusions is not permitted.";
                          list end-point-pair {
                            must "end-point1 != end-point2" {
                              error-message "The two UNI IDs for a given inclusion cannot be the same.";
                              description
                                "The two UNI IDs for a given inclusion cannot be the same.";
                              reference "[MEF10.3] [R32].";
                            }
                            must "(../../../../../../../../../connection-type != 'rooted-multipoint') or ((../../../../../../../../../connection-type = 'rooted-multipoint') and not((../../../../../../../../../end-points/end-point[uni-id = current()/end-point1]/role = 'leaf') and (../../../../../../../../../end-points/end-point[uni-id = current()/end-point2]/role = 'leaf')))" {
                              error-message "If EVC Type is Rooted-Multipoint, sls-uni-inclusion UNI Pairs cannot both be role 'leaf'.";
                              description
                                "If EVC Type is Rooted-Multipoint, sls-uni-inclusion UNI Pairs cannot both be role 'leaf'.";
                              reference "[MEF10.3].";
                            }
                            key "end-point1 end-point2";
                            description
                              "EVC: Defines the EVC End Points (UNI) Pairs that must conform to the EVC's SLS Performance Metrics. Use of this list indicates that a complete set of UNI Pairs has been specified for the Performance Metrics defined in the selected SLS.";
                            leaf end-point1 {
                              type leafref {
                                path "../../../../../../../../../../end-points/end-point/uni-id";
                              }
                              description
                                "EVC: The UNI ID paired with the EVC ID in the containing list.";
                              reference "[MEF10.3] Section 8.3, Section 10.1.  [MEF7.3] Section 7.11.";
                            }
                            leaf end-point2 {
                              type leafref {
                                path "../../../../../../../../../../end-points/end-point/uni-id";
                              }
                              description
                                "EVC: The UNI ID paired with the EVC ID in the containing list.";
                              reference "[MEF10.3] Section 8.3, Section 10.1.  [MEF7.3] Section 7.11.";
                            }
                          }
                        }
                        container sls-uni-exclusions {
                          presence "Not all EVC End Points (UNI) must conform to the EVC SLS Performance Metrics.";
                          description
                            "EVC: Not all EVC End Points (UNI) must conform to the EVC SLS Performance Metrics. Use of this list indicates that all UNI Pairs EXCEPT for the ones indicated (per Performance Metric) must conform to the SLS.";
                          list end-point-pair {
                            must "end-point1 != end-point2" {
                              error-message "The two UNI IDs for a given exclusion cannot be the same.";
                              description
                                "The two UNI IDs for a given exclusion cannot be the same as these pairs are invalid as defined in MEF 10.3.";
                              reference "[MEF10.3] [R32].";
                            }
                            key "end-point1 end-point2";
                            description
                              "SLS UNI Exclusions List. The following pairs of UNI Interconnections are not required meet the SLS Performance Objectives. Configing both SLS UNI Inclusions and SLS UNI Exclusions is not permitted.";
                            leaf end-point1 {
                              type leafref {
                                path "../../../../../../../../../../end-points/end-point/uni-id";
                              }
                              description
                                "EVC: The UNI ID paired with the EVC ID in the containing list.";
                              reference "[MEF10.3] Section 8.3, Section 10.1.  [MEF7.3] Section 7.11.";
                            }
                            leaf end-point2 {
                              type leafref {
                                path "../../../../../../../../../../end-points/end-point/uni-id";
                              }
                              description
                                "EVC: The UNI ID paired with the EVC ID in the containing list.";
                              reference "[MEF10.3] Section 8.3, Section 10.1.  [MEF7.3] Section 7.11.";
                            }
                          }
                        }
                      }
                    }
                    container end-point-pairs {
                      when "not(/mef-global:mef-global/mef-global:sls-profiles/mef-global:sls-profile[mef-global:sls-id = current()/../../../../../sls-id]/mef-global:pm-cos-name-entries/mef-global:pm-cos-name-entry[mef-global:cos-name = current()/../../../cos-name]/mef-global:pm-entries/mef-global:pm-entry[mef-global:pm-entry-id=current()/../pm-entry-id]/mef-global:one-way-group-availability-pm)" {
                        description
                          "Only visible when one-way-group-availability-pm is not being configured.";
                      }
                      must "not(sls-uni-inclusions) or (sls-uni-inclusions and not(sls-uni-exclusions))" {
                        error-message "The EVC Performance SLS Exclusions and Inclusions List cannot both be configured for an EVC.";
                        description
                          "The EVC Performance SLS Exclusions and Inclusions List cannot both be configured for an EVC.";
                        reference "[MEF10.3] [R37].";
                      }
                      must "(../../../../../../connection-type != 'rooted-multipoint') or ((../../../../../../connection-type = 'rooted-multipoint') and not(sls-uni-exclusions) )" {
                        error-message "If EVC Type is Rooted-Multipoint, sls-uni-inclusions must be used instead of sls-uni-exclusions.";
                        description
                          "If EVC Type is Rooted-Multipoint, sls-uni-inclusions must be used instead of sls-uni-exclusions.";
                        reference "[MEF10.3] [R37].";
                      }
                      description
                        "End Point Pairs";
                      container sls-uni-inclusions {
                        presence "EVC: Defines the EVC End Points (UNI) Pairs that must conform to the EVC's SLS Performance Metrics.";
                        description
                          "SLS UNI Inclusions List. The following pairs of UNI Interconnections are to required to meet the SLS Performance Objectives. Configing both SLS UNI Inclusions and SLS UNI Exclusions is not permitted.";
                        list end-point-pair {
                          must "end-point1 != end-point2" {
                            error-message "The two UNI IDs for a given inclusion cannot be the same.";
                            description
                              "The two UNI IDs for a given inclusion cannot be the same.";
                            reference "[MEF10.3].";
                          }
                          must "(../../../../../../../../connection-type != 'rooted-multipoint') or ((../../../../../../../../connection-type = 'rooted-multipoint') and not((../../../../../../../../end-points/end-point[uni-id = current()/end-point1]/role = 'leaf') and (../../../../../../../../end-points/end-point[uni-id = current()/end-point2]/role = 'leaf')))" {
                            error-message "If EVC Type is Rooted-Multipoint, sls-uni-inclusion UNI Pairs cannot both be role 'leaf'.";
                            description
                              "If EVC Type is Rooted-Multipoint, sls-uni-inclusion UNI Pairs cannot both be role 'leaf'.";
                            reference "[MEF10.3] [R37].";
                          }
                          key "end-point1 end-point2";
                          description
                            "EVC: Defines the EVC End Points (UNI) Pairs that must conform to the EVC's SLS Performance Metrics. Use of this list indicates that a complete set of UNI Pairs has been specified for the Performance Metrics defined in the selected SLS.";
                          leaf end-point1 {
                            type leafref {
                              path "../../../../../../../../../end-points/end-point/uni-id";
                            }
                            description
                              "EVC: The UNI ID paired with the EVC ID in the containing list.";
                            reference "[MEF10.3] Section 8.3, Section 10.1.  [MEF7.3] Section 7.11.";
                          }
                          leaf end-point2 {
                            type leafref {
                              path "../../../../../../../../../end-points/end-point/uni-id";
                            }
                            description
                              "EVC: The UNI ID paired with the EVC ID in the containing list.";
                            reference "[MEF10.3] Section 8.3, Section 10.1.  [MEF7.3] Section 7.11.";
                          }
                        }
                      }
                      container sls-uni-exclusions {
                        presence "Not all EVC End Points (UNI) must conform to the EVC SLS Performance Metrics.";
                        description
                          "EVC: Not all EVC End Points (UNI) must conform to the EVC SLS Performance Metrics. Use of this list indicates that all UNI Pairs EXCEPT for the ones indicated (per Performance Metric) must conform to the SLS.";
                        list end-point-pair {
                          must "end-point1 != end-point2" {
                            error-message "The two UNI IDs for a given exclusion cannot be the same.";
                            description
                              "The two UNI IDs for a given exclusion cannot be the same as these pairs are invalid as defined in MEF 10.3.";
                            reference "[MEF10.3].";
                          }
                          key "end-point1 end-point2";
                          description
                            "SLS UNI Exclusions List. The following pairs of UNI Interconnections are not required meet the SLS Performance Objectives. Configing both SLS UNI Inclusions and SLS UNI Exclusions is not permitted.";
                          leaf end-point1 {
                            type leafref {
                              path "../../../../../../../../../end-points/end-point/uni-id";
                            }
                            description
                              "EVC: The UNI ID paired with the EVC ID in the containing list.";
                            reference "[MEF10.3] Section 8.3, Section 10.1.  [MEF7.3] Section 7.11.";
                          }
                          leaf end-point2 {
                            type leafref {
                              path "../../../../../../../../../end-points/end-point/uni-id";
                            }
                            description
                              "EVC: The UNI ID paired with the EVC ID in the containing list.";
                            reference "[MEF10.3] Section 8.3, Section 10.1.  [MEF7.3] Section 7.11.";
                          }
                        }
                      }
                    }
                  }
                }
              }
            }
          }
          leaf connection-type {
            type mef-types:connection-type;
            must "(. != 'point-to-point') or ((. = 'point-to-point') and (count(../end-points/end-point[role = 'leaf']) = 0))" {
              error-message "If EVC Type is Point-to-Point, all UNI Roles must be root.";
              description
                "If EVC Type is Point-to-Point, all UNI Roles must be root.";
              reference "[MEF10.3] [R12].";
            }
            must "(. != 'multipoint-to-multipoint') or ((. = 'multipoint-to-multipoint') and (count(../end-points/end-point[role = 'leaf']) = 0))" {
              error-message "If EVC Type is Multipoint-to-Multipoint, all UNI Roles must be root.";
              description
                "If EVC Type is Multipoint-to-Multipoint, all UNI Roles must be root.";
              reference "[MEF10.3] [R12].";
            }
            must "(. != 'rooted-multipoint') or ((. = 'rooted-multipoint') and (count(../end-points/end-point[role = 'root']) > 0) )" {
              error-message "If EVC Type is Rooted-Multipoint, one or more UNI Roles must be root.";
              description
                "If EVC Type is Rooted-Multipoint, one or more UNI Roles must be root.";
              reference "[MEF10.3] [R54].";
            }
            must "(. != 'point-to-point') or ((. = 'point-to-point') and (count(../end-points/end-point) = 2))" {
              error-message "If EVC Type is Point-to-Point, there must be exactly 2 UNI configured for the EVC.";
              description
                "If EVC Type is Point-to-Point, there must be exactly 2 UNI configured for the EVC.";
              reference "[MEF10.3] [R9].";
            }
            must "(. != 'multipoint-to-multipoint') or ((. = 'multipoint-to-multipoint') and (count(../end-points/end-point) > 1) and (count(../end-points/end-point) <= ../max-num-of-evc-end-point))" {
              error-message "If EVC Type is Multipoint-to-Multipoint, there must be 2 or more UNI configured for the EVC.";
              description
                "If EVC Type is Multipoint-to-Multipoint, there must be 2 or more UNI configured for the EVC.";
              reference "[MEF10.3] [R9].";
            }
            must "(. != 'rooted-multipoint') or ((. = 'rooted-multipoint') and (count(../end-points/end-point) > 1) and (count(../end-points/end-point) <= ../max-num-of-evc-end-point))" {
              error-message "If EVC Type is Rooted-Multipoint, there must be 2 or more UNI configured for the EVC.";
              description
                "If EVC Type is Rooted-Multipoint, there must be 2 or more UNI configured for the EVC.";
              reference "[MEF10.3] [R9].";
            }
            must "(. != 'point-to-point') or ((. = 'point-to-point') and (../max-num-of-evc-end-point = 2))" {
              error-message "If EVC Type is Point-to-Point, the value of max-num-of-evc-end-point must be 2.";
              description
                "If EVC Type is Point-to-Point, the value of max-num-of-evc-end-point must be 2.";
              reference "[MEF10.3] [R9].";
            }
            must "(. != 'multipoint-to-multipoint') or ((. = 'multipoint-to-multipoint') and (../max-num-of-evc-end-point > 2))" {
              error-message "If EVC Type is Multipoint-to-Multipoint, the value of max-num-of-evc-end-point must be at least 3.";
              description
                "If EVC Type is Multipoint-to-Multipoint, the value of max-num-of-evc-end-point must be at least 3.";
              reference "[MEF10.3] [R9].";
            }
            must "(. != 'rooted-multipoint') or ((. = 'rooted-multipoint') and (../max-num-of-evc-end-point > 2))" {
              error-message "If EVC Type is Rooted-Multipoint, the value of max-num-of-evc-end-point must be at least 3.";
              description
                "MEF 10.3 [R9 B RM] If EVC Type is Rooted-Multipoint, the value of max-num-of-evc-end-point must be at least 3.";
              reference "[MEF10.3] [R9].";
            }
            mandatory true;
            description
              "This EVC attribute describes the EVC as either Multipoint-To-Multipoint, Point-To-Point, or Rooted-Multipoint.";
            reference "[MEF10.3] Section 8.1, [R4], [R5], [R10], [R11], [R12], [R13] and [R14].[MEF7.3] Section 7.1.";
          }
          leaf admin-state {
            type boolean;
            default "true";
            description
              "EVC: Locked/Unlocked is inconsistent with Oper Status and will be confusing.";
            reference "[MEF15]. [MEF7.3] Section 7.1.";
          }
          leaf user-label {
            type mef-types:identifier1023;
            description
              "EVC: User Label.";
            reference "[MEF7.3] Section 7.1.";
          }
          leaf max-frame-size {
            type mef-types:max-svc-frame-size-type;
            description
              "EVC: Maximum Frame Size in bytes.";
            reference "[MEF10.3] Section 8.9.[MEF7.3] Section 7.1.";
          }
          leaf max-num-of-evc-end-point {
            type uint32 {
              range "2..max";
            }
            must "(. > 2) or ((. = 2) and (../connection-type = 'point-to-point'))" {
              error-message "If EVC Type is Point-to-Point, the max-num-of-evc-end-point value must be 2.";
              description
                "If EVC Type is Point-to-Point, the max-num-of-evc-end-point value must be 2.";
              reference "[MEF10.3] [R13].";
            }
            must "(. = 2) or ((. > 2) and ((../connection-type = 'multipoint-to-multipoint') or (../connection-type = 'rooted-multipoint')))" {
              error-message "If EVC Type is Multipoint-to-Multipoint or Rooted-Multipoint, the max-num-of-evc-end-point value must be at least 3.";
              description
                "If EVC Type is Multipoint-to-Multipoint or Rooted-Multipoint, the max-num-of-evc-end-point value must be at least 3.";
              reference "[MEF10.3] [R14]. [MEF6.2] [R54].";
            }
            mandatory true;
            description
              "EVC:The Maximum Number of UNIs this EVC can be configured for. If EVC Type is Multipoint-to-Multipoint or Rooted-Multipoint, the max-num-of-evc-end-point value must be at least 3. This value must be 2 for point-to-point mode.";
            reference "[MEF10.3] [R14]. [MEF7.3] Section 7.2.";
          }
          leaf ce-vlan-id-preservation {
            type boolean;
            default "false";
            description
              "EVC: Preserve CE-VLAN ID.";
            reference "[MEF10.3] Section 8.6.1, [R24] [R25], Section 9.10.2, Section 9.12, [R81], Figure 20. [MEF7.3] Section 7.2.";
          }
          leaf ce-vlan-pcp-preservation {
            type boolean;
            default "false";
            description
              "EVC: Enables CE-VLAN PCP (CoS) preservation for the EVC, as described in MEF 10.3 section 8.6.2).";
            reference "[MEF10.3] Section 8.6.2, [R26]. [MEF7.3] Section 7.1.";
          }
          leaf ce-vlan-dei-preservation {
            type boolean;
            default "false";
            description
              "EVC: Enables CE-VLAN DEI preservation for the EVC. When this is enabled, if a C-tagged ingress Service frame results in a C-tagged egress Service frame, the DEI bit in the egress frame has the same value as the DEI bit in the ingress frame.";
            reference "[MEF10.3] Section 8.6.2, [R26]. [MEF7.3] Section 7.1.";
          }
          leaf unicast-frame-delivery {
            type mef-types:data-svc-frame-delivery-type;
            default "unconditional";
            description
              "EVC: Unicast Data Service Frame Delivery Mode (unconditional[default], conditional, or discard).";
            reference "[MEF10.3] Section 8.5.2,[R16], [R17], Section 8.8, Section 11. [MEF7.3] Section 7.1.";
          }
          leaf multicast-frame-delivery {
            type mef-types:data-svc-frame-delivery-type;
            default "unconditional";
            description
              "EVC: Multicast Data Service Frame Delivery Mode (unconditional[default], conditional, or discard).";
            reference "[MEF10.3] Section 8.5.2, [R16], [R18], Section 8.8, Section 11. [MEF7.3] Section 7.1.";
          }
          leaf broadcast-frame-delivery {
            type mef-types:data-svc-frame-delivery-type;
            default "unconditional";
            description
              "EVC: Broadcast Data Service Frame Delivery Mode (unconditional[default], conditional, or discard).";
            reference "[MEF10.3] Section 8.5.2, [R16], [R19], Section 8.8, Section 11. [MEF7.3] Section 7.1.";
          }
          leaf svc-type {
            type mef-types:mef-service-type;
            must "(. != 'epl') or ((. = 'epl') and (count(/mef-interfaces:mef-interfaces/mef-interfaces:unis/mef-interfaces:uni[mef-interfaces:uni-id = current()/../mef-services:end-points/mef-services:end-point/mef-services:uni-id][mef-interfaces:uni-id/../mef-interfaces:service-multiplexing-enabled = 'true']) = 0))" {
              error-message "For EPL, Service Multiplexing must be disabled for all UNIs in the EVC UNI List.";
              description
                "MEF 6.2 [R19] For EPL, Service Multiplexing must be disabled for all UNIs in the EVC UNI List.";
              reference "[MEF6.2] [R19].";
            }
            must "(. != 'epl') or ((. = 'epl') and (count(/mef-interfaces:mef-interfaces/mef-interfaces:unis/mef-interfaces:uni[mef-interfaces:uni-id = current()/../mef-services:end-points/mef-services:end-point/mef-services:uni-id][mef-interfaces:uni-id/../mef-interfaces:bundling-enabled = 'true']) = 0))" {
              error-message "For EPL, Bundling must be disabled for all UNIs in the EVC UNI List.";
              description
                "For EPL, Bundling must be disabled for all UNIs in the EVC UNI List.";
              reference "[MEF6.2] [R20].";
            }
            must "(. != 'epl') or ((. = 'epl') and (count(/mef-interfaces:mef-interfaces/mef-interfaces:unis/mef-interfaces:uni[mef-interfaces:uni-id = current()/../mef-services:end-points/mef-services:end-point/mef-services:uni-id][mef-interfaces:uni-id/../mef-interfaces:all-to-one-bundling-enabled = 'false']) = 0))" {
              error-message "For EPL, All-to-One Bundling must be enabled for all UNIs in the EVC UNI List.";
              description
                "For EPL, All-to-One Bundling must be enabled for all UNIs in the EVC UNI List.";
              reference "[MEF6.2] [R21].";
            }
            must "(. != 'epl') or ((. = 'epl') and (count(/mef-interfaces:mef-interfaces/mef-interfaces:unis/mef-interfaces:uni[mef-interfaces:uni-id = current()/../mef-services:end-points/mef-services:end-point/mef-services:uni-id][mef-interfaces:uni-id/../mef-interfaces:max-num-of-evcs != 1]) = 0))" {
              error-message "For EPL, Max EVC Count must be 1 for all UNIs in the EVC UNI List.";
              description
                "For EPL, Max EVC Count must be 1 for all UNIs in the EVC UNI List.";
              reference "[MEF6.2] [R22].";
            }
            must "(. != 'epl') or ((. = 'epl') and (count(../end-points/end-point/egress-bwp-flows-per-eec/bwp-flow-per-eec) = 0))" {
              error-message "For EPL, Egress Bandwidth Profile per Egress Equivalence Class cannot be set for all UNIs in the EVC per UNI List.";
              description
                "For EPL, Egress Bandwidth Profile per Egress Equivalence Class cannot be set for all UNIs in the EVC per UNI List.";
              reference "[MEF6.2] [R23].";
            }
            must "(. != 'epl') or ((. = 'epl') and (count(../end-points/end-point[source-mac-address-limit]) = 0) )" {
              error-message "For EPL, Source MAC Address Limit must be disabled.";
              description
                "For EPL, Source MAC Address Limit must be disabled.";
              reference "[MEF6.2] [R24].";
            }
            must "(. != 'epl') or ((. = 'epl') and (../connection-type = 'point-to-point'))" {
              error-message "For EPL, EVC Type must be Point-to-Point.";
              description
                "For EPL, EVC Type must be Point-to-Point.";
              reference "[MEF6.2] [R25].";
            }
            must "(. != 'epl') or ((. = 'epl') and (../unicast-frame-delivery = 'unconditional'))" {
              error-message "For EPL, unicast-frame-delivery must be unconditional.";
              description
                "For EPL, unicast-frame-delivery must be unconditional.";
              reference "[MEF6.2] [R26].";
            }
            must "(. != 'epl') or ((. = 'epl') and (../multicast-frame-delivery = 'unconditional'))" {
              error-message "For EPL, multicast-frame-delivery must be unconditional.";
              description
                "For EPL, multicast-frame-delivery must be unconditional.";
              reference "[MEF6.2] [R27].";
            }
            must "(. != 'epl') or ((. = 'epl') and (../broadcast-frame-delivery = 'unconditional'))" {
              error-message "For EPL, broadcast-frame-delivery must be unconditional.";
              description
                "For EPL, broadcast-frame-delivery must be unconditional.";
              reference "[MEF6.2] [R28].";
            }
            must "(. != 'epl') or ((. = 'epl') and (../ce-vlan-id-preservation = 'true'))" {
              error-message "For EPL, CE-VLAN ID Preservation must be enabled.";
              description
                "MEF 6.2 [R29] For EPL, CE-VLAN ID Preservation must be enabled.";
            }
            must "(. != 'epl') or ((. = 'epl') and (../ce-vlan-pcp-preservation = 'true'))" {
              error-message "For EPL, CE-VLAN ID CoS Preservation must be enabled.";
              description
                "For EPL, CE-VLAN ID CoS Preservation must be enabled.";
              reference "[MEF6.2] [R30].";
            }
            must "(. != 'evpl') or ((. = 'evpl') and (count(/mef-interfaces:mef-interfaces/mef-interfaces:unis/mef-interfaces:uni[mef-interfaces:uni-id = current()/../mef-services:end-points/mef-services:end-point/mef-services:uni-id][mef-interfaces:uni-id/../mef-interfaces:all-to-one-bundling-enabled = 'true']) = 0))" {
              error-message "For EVPL, All-to-One Bundling must be disabled for all UNIs in the EVC UNI List.";
              description
                "For EVPL, All-to-One Bundling must be disabled for all UNIs in the EVC UNI List.";
              reference "[MEF6.2] [R31].";
            }
            must "(. != 'evpl') or ((. = 'evpl') and ((../unicast-frame-delivery != 'unconditional') or (../multicast-frame-delivery != 'unconditional') or (../broadcast-frame-delivery != 'unconditional') or count(../end-points/end-point[source-mac-address-limit]) = 0))" {
              error-message "For EVPL, Source MAC Address Limit must be disabled for all UNIs in the EVC per UNI List if all 3 -svc-frm-delivery values are unconditional.";
              description
                "For EVPL, Source MAC Address Limit must be disabled for all UNIs in the EVC per UNI List if all 3 -svc-frm-delivery values are unconditional.";
              reference "[MEF6.2] [R32].";
            }
            must "(. != 'evpl') or ((. = 'evpl') and (../connection-type = 'point-to-point'))" {
              error-message "For EVPL, EVC Type must be Point-to-Point.";
              description
                "For EVPL, EVC Type must be Point-to-Point.";
              reference "[MEF6.2] [R33].";
            }
            must "(. != 'eplan') or ((. = 'eplan') and (count(/mef-interfaces:mef-interfaces/mef-interfaces:unis/mef-interfaces:uni[mef-interfaces:uni-id = current()/../mef-services:end-points/mef-services:end-point/mef-services:uni-id][mef-interfaces:uni-id/../mef-interfaces:service-multiplexing-enabled = 'true']) = 0))" {
              error-message "For EP-LAN, Service Multiplexing must be disabled for all UNIs in the EVC UNI List.";
              description
                "For EP-LAN, Service Multiplexing must be disabled for all UNIs in the EVC UNI List.";
              reference "[MEF6.2] [R34].";
            }
            must "(. != 'eplan') or ((. = 'eplan') and (count(/mef-interfaces:mef-interfaces/mef-interfaces:unis/mef-interfaces:uni[mef-interfaces:uni-id = current()/../mef-services:end-points/mef-services:end-point/mef-services:uni-id][mef-interfaces:uni-id/../mef-interfaces:bundling-enabled = 'true']) = 0))" {
              error-message "For EP-LAN, Bundling must be disabled for all UNIs in the EVC UNI List.";
              description
                "For EP-LAN, Bundling must be disabled for all UNIs in the EVC UNI List.";
              reference "[MEF6.2] [R35].";
            }
            must "(. != 'eplan') or ((. = 'eplan') and (count(/mef-interfaces:mef-interfaces/mef-interfaces:unis/mef-interfaces:uni[mef-interfaces:uni-id = current()/../mef-services:end-points/mef-services:end-point/mef-services:uni-id][mef-interfaces:uni-id/../mef-interfaces:all-to-one-bundling-enabled = 'false']) = 0))" {
              error-message "For EP-LAN, All-to-One Bundling must be enabled for all UNIs in the EVC UNI List.";
              description
                "For EP-LAN, All-to-One Bundling must be enabled for all UNIs in the EVC UNI List.";
              reference "[MEF6.2] [R36].";
            }
            must "(. != 'eplan') or ((. = 'eplan') and (count(/mef-interfaces:mef-interfaces/mef-interfaces:unis/mef-interfaces:uni[mef-interfaces:uni-id = current()/../mef-services:end-points/mef-services:end-point/mef-services:uni-id][mef-interfaces:uni-id/../mef-interfaces:max-num-of-evcs != 1]) = 0))" {
              error-message "For EP-LAN, Max EVC Count must be 1 for all UNIs in the EVC UNI List.";
              description
                "For EP-LAN, Max EVC Count must be 1 for all UNIs in the EVC UNI List.";
              reference "[MEF6.2] [R37].";
            }
            must "(. != 'eplan') or ((. = 'eplan') and (../connection-type = 'multipoint-to-multipoint'))" {
              error-message "For EP-LAN, EVC Type must be Multipoint-to-Multipoint.";
              description
                "For EP-LAN, EVC Type must be Multipoint-to-Multipoint.";
              reference "[MEF6.2] [R38].";
            }
            must "(. != 'eplan') or ((. = 'eplan') and (../ce-vlan-id-preservation = 'true'))" {
              error-message "For EP-LAN, CE-VLAN ID Preservation must be enabled.";
              description
                "For EP-LAN, CE-VLAN ID Preservation must be enabled.";
              reference "[MEF6.2] [R39].";
            }
            must "(. != 'eplan') or ((. = 'eplan') and (../ce-vlan-pcp-preservation = 'true'))" {
              error-message "For EP-LAN, CE-VLAN ID CoS Preservation must be enabled.";
              description
                "For EP-LAN, CE-VLAN ID CoS Preservation must be enabled.";
              reference "[MEF6.2] [R40].";
            }
            must "(. != 'evplan') or ((. = 'evplan') and (../connection-type = 'multipoint-to-multipoint'))" {
              error-message "For EVP-LAN, EVC Type must be Multipoint-to-Multipoint.";
              description
                "For EVP-LAN, EVC Type must be Multipoint-to-Multipoint.";
              reference "[MEF6.2] [R42].";
            }
            must "(. != 'evplan') or ((. = 'evplan') and (count(/mef-interfaces:mef-interfaces/mef-interfaces:unis/mef-interfaces:uni[mef-interfaces:uni-id = current()/../mef-services:end-points/mef-services:end-point/mef-services:uni-id][mef-interfaces:uni-id/../mef-interfaces:all-to-one-bundling-enabled = 'true']) = 0))" {
              error-message "For EVP-LAN, All-to-One Bundling must be disabled for all UNIs in the EVC UNI List.";
              description
                "For EVP-LAN, All-to-One Bundling must be disabled for all UNIs in the EVC UNI List.";
              reference "[MEF6.2] [R41].";
            }
            must "(. != 'eptree') or ((. = 'eptree') and (count(/mef-interfaces:mef-interfaces/mef-interfaces:unis/mef-interfaces:uni[mef-interfaces:uni-id = current()/../mef-services:end-points/mef-services:end-point/mef-services:uni-id][mef-interfaces:uni-id/../mef-interfaces:service-multiplexing-enabled = 'true']) = 0))" {
              error-message "For EP-TREE, Service Multiplexing must be disabled for all UNIs in the EVC UNI List.";
              description
                "For EP-TREE, Service Multiplexing must be disabled for all UNIs in the EVC UNI List.";
              reference "[MEF6.2] [R43].";
            }
            must "(. != 'eptree') or ((. = 'eptree') and (count(/mef-interfaces:mef-interfaces/mef-interfaces:unis/mef-interfaces:uni[mef-interfaces:uni-id = current()/../mef-services:end-points/mef-services:end-point/mef-services:uni-id][mef-interfaces:uni-id/../mef-interfaces:bundling-enabled = 'true']) = 0))" {
              error-message "For EP-TREE, Bundling must be disabled for all UNIs in the EVC UNI List.";
              description
                "For EP-TREE, Bundling must be disabled for all UNIs in the EVC UNI List.";
              reference "[MEF6.2] [R44].";
            }
            must "(. != 'eptree') or ((. = 'eptree') and (count(/mef-interfaces:mef-interfaces/mef-interfaces:unis/mef-interfaces:uni[mef-interfaces:uni-id = current()/../mef-services:end-points/mef-services:end-point/mef-services:uni-id][mef-interfaces:uni-id/../mef-interfaces:all-to-one-bundling-enabled = 'false']) = 0))" {
              error-message "For EP-TREE, All-to-One Bundling must be enabled for all UNIs in the EVC UNI List.";
              description
                "For EP-TREE, All-to-One Bundling must be enabled for all UNIs in the EVC UNI List.";
              reference "[MEF6.2] [R45].";
            }
            must "(. != 'eptree') or ((. = 'eptree') and (count(/mef-interfaces:mef-interfaces/mef-interfaces:unis/mef-interfaces:uni[mef-interfaces:uni-id = current()/../mef-services:end-points/mef-services:end-point/mef-services:uni-id][mef-interfaces:uni-id/../mef-interfaces:max-num-of-evcs != 1]) = 0))" {
              error-message "For EP-TREE, Max EVC Count must be 1 for all UNIs in the EVC UNI List.";
              description
                "For EP-TREE, Max EVC Count must be 1 for all UNIs in the EVC UNI List.";
              reference "[MEF6.2] [R46].";
            }
            must "(. != 'eptree') or ((. = 'eptree') and (../connection-type = 'rooted-multipoint'))" {
              error-message "For EP-TREE, EVC Type must be Rooted-Multipoint.";
              description
                "For EP-TREE, EVC Type must be Rooted-Multipoint.";
              reference "[MEF6.2] [R47].";
            }
            must "(. != 'eptree') or ((. = 'eptree') and (../ce-vlan-id-preservation = 'true'))" {
              error-message "For EP-TREE, CE-VLAN ID Preservation must be enabled.";
              description
                "For EP-TREE, CE-VLAN ID Preservation must be enabled.";
              reference "[MEF6.2] [R49].";
            }
            must "(. != 'eptree') or ((. = 'eptree') and (../ce-vlan-pcp-preservation = 'true'))" {
              error-message "For EP-TREE, CE-VLAN ID CoS Preservation must be enabled.";
              description
                "For EP-TREE, CE-VLAN ID CoS Preservation must be enabled.";
              reference "[MEF6.2] [R50].";
            }
            must "(. != 'evptree') or ((. = 'evptree') and (count(/mef-interfaces:mef-interfaces/mef-interfaces:unis/mef-interfaces:uni[mef-interfaces:uni-id = current()/../mef-services:end-points/mef-services:end-point/mef-services:uni-id][mef-interfaces:uni-id/../mef-interfaces:all-to-one-bundling-enabled = 'true']) = 0))" {
              error-message "For EVP-TREE, All-to-One Bundling must be disabled for all UNIs in the EVC UNI List.";
              description
                "For EVP-TREE, All-to-One Bundling must be disabled for all UNIs in the EVC UNI List.";
              reference "[MEF6.2] [R51].";
            }
            must "(. != 'evptree') or ((. = 'evptree') and (../connection-type = 'rooted-multipoint'))" {
              error-message "For EVP-TREE, EVC Type must be Rooted-Multipoint.";
              description
                "For EVP-TREE, EVC Type must be Rooted-Multipoint.";
              reference "[MEF6.2] [R52].";
            }
            default "other";
            description
              "The MEF Service Type.";
          }
        }
      }
    }
  }
}
