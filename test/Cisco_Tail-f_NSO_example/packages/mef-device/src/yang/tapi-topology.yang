module tapi-topology {
    namespace "urn:onf:params:xml:ns:yang:TapiTopology";
    prefix tapi-topology;
    import tapi {
      prefix tapi;
    }
    import ietf-network {
      prefix net;
    }
    import ietf-network-topology {
      prefix topo;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-10-06 {
        description "Latest revision";
        reference "RFC 6020 and RFC 6087";
    }

    augment "/net:network/topo:link" {
      description
        "Add T-API parameters to links in the IETF topology model.";
      uses link-attrs;
    }

    grouping link-attrs {
            container state {
                uses tapi:admin-state-pac;
                description "none";
            }
            container transfer-capacity {
                uses transfer-capacity-pac;
                description "none";
            }
            container transfer-cost {
                uses transfer-cost-pac;
                description "none";
            }
            container transfer-integrity {
                uses transfer-integrity-pac;
                description "none";
            }
            container transfer-timing {
                uses transfer-timing-pac;
                description "none";
            }
            container risk-parameter {
                uses risk-parameter-pac;
                description "none";
            }
            container validation {
                uses validation-pac;
                description "none";
            }
            container lp-transition {
                uses layer-protocol-transition-pac;
                description "none";
            }
            leaf-list layer-protocol-name {
                type tapi:layer-protocol-name;
                description "none";
            }
            leaf direction {
                type tapi:forwarding-direction;
                description "The directionality of the Link. 
                    Is applicable to simple Links where all LinkEnds are BIDIRECTIONAL (the Link will be BIDIRECTIONAL) or UNIDIRECTIONAL (the Link will be UNIDIRECTIONAL). 
                    Is not present in more complex cases.";
            }
            description "The Link object class models effective adjacency between two or more ForwardingDomains (FD). ";
        }

    augment "/net:network/net:node" {
      description
        "Add T-API parameters to nodes in the IETF network model.";
      uses node-attrs;
    }

        grouping node-attrs {
            container state {
                uses tapi:admin-state-pac;
                description "none";
            }
            container transfer-capacity {
                uses transfer-capacity-pac;
                description "none";
            }
            container transfer-cost {
                uses transfer-cost-pac;
                description "none";
            }
            container transfer-integrity {
                uses transfer-integrity-pac;
                description "none";
            }
            container transfer-timing {
                uses transfer-timing-pac;
                description "none";
            }
            leaf-list layer-protocol-name {
                type tapi:layer-protocol-name;
                description "none";
            }
            uses tapi:resource;
            description "The ForwardingDomain (FD) object class models the “ForwardingDomain” topological component which is used to effect forwarding of transport characteristic information and offers the potential to enable forwarding. 
                At the lowest level of recursion, an FD (within a network element (NE)) represents a switch matrix (i.e., a fabric). Note that an NE can encompass multiple switch matrices (FDs). ";
        }

        grouping topology-attrs {
            leaf-list layer-protocol-name {
                type tapi:layer-protocol-name;
                min-elements 1;
                description "none";
            }
            description
              "The ForwardingDomain (FD) object class models the “ForwardingDomain” topological component which
               is used to effect forwarding of transport characteristic information and offers
               the potential to enable forwarding.  At the lowest level of recursion, an FD
               (within a network element (NE)) represents a switch matrix (i.e., a fabric). Note
               that an NE can encompass multiple switch matrices (FDs).";
        }

        grouping layer-protocol-transition-pac {
            leaf-list transitioned-layer-protocol-name {
                type string;
                description "Provides the ordered structure of layer protocol transitions encapsulated in the TopologicalEntity. The ordering relates to the LinkPort role.";
            }
            description "Relevant for a Link that is formed by abstracting one or more LTPs (in a stack) to focus on the flow and deemphasize the protocol transformation. 
                This abstraction is relevant when considering multi-layer routing. 
                The layer protocols of the LTP and the order of their application to the signal is still relevant and need to be accounted for. This is derived from the LTP spec details.
                This Pac provides the relevant abstractions of the LTPs and provides the necessary association to the LTPs involved.
                Links that included details in this Pac are often referred to as Transitional Links.";
        }

        augment "/net:network/topo:link/topo:source" {
          description
            "Add T-API parameters to link endpoint in the IETF topology model.";
          uses link-port-attrs;
        }

        augment "/net:network/topo:link/topo:destination" {
          description
            "Add T-API parameters to link endpoint in the IETF topology model.";
          uses link-port-attrs;
        }

        grouping link-port-attrs {
            leaf role {
                type tapi:port-role;
                description "Each LinkEnd of the Link has a role (e.g., symmetric, hub, spoke, leaf, root)  in the context of the Link with respect to the Link function. ";
            }
            leaf direction {
                type tapi:port-direction;
                description "The orientation of defined flow at the LinkEnd.";
            }
            description "The association of the Link to LTPs is made via LinkEnd.
                The LinkEnd object class models the access to the Link function. 
                The traffic forwarding between the associated LinkEnds of the Link depends upon the type of Link.  
                In cases where there is resilience the LinkEnd may convey the resilience role of the access to the Link. 
                The Link can be considered as a component and the LinkEnd as a Port on that component";
        }

        augment "/net:network/net:node/topo:termination-point" {
          description
            "Add T-API parameters to termination points in the IETF topology model.";
          uses node-edge-point-attrs;
        }

        grouping node-edge-point-attrs {
            list layer-protocol {
                key 'local-id';
                uses tapi:layer-protocol;
                description "none";
            }
            container state {
                uses tapi:admin-state-pac;
                description "none";
            }
            leaf direction {
                type tapi:termination-direction;
                description "none";
            }
            description "The LogicalTerminationPoint (LTP) object class encapsulates the termination and adaptation functions of one or more transport layers. 
                The structure of LTP supports all transport protocols including circuit and packet forms.";
        }
        grouping risk-parameter-pac {
            list risk-characteristic {
                key 'risk-characteristic-name';
                uses risk-characteristic;
                description "A list of risk characteristics for consideration in an analysis of shared risk. Each element of the list represents a specific risk consideration.";
            }
            description "The risk characteristics of a TopologicalEntity come directly from the underlying physical realization. 
                The risk characteristics propagate from the physical realization to the client and from the server layer to the client layer, this propagation may be modified by protection.
                A TopologicalEntity may suffer degradation or failure as a result of a problem in a part of the underlying realization.
                The realization can be partitioned into segments which have some relevant common failure modes.
                There is a risk of failure/degradation of each segment of the underlying realization.
                Each segment is a part of a larger physical/geographical unit that behaves as one with respect to failure (i.e. a failure will have a high probability of impacting the whole unit (e.g. all cables in the same duct).
                Disruptions to that larger physical/geographical unit will impact (cause failure/errors to) all TopologicalEntities that use any part of that larger physical/geographical entity.
                Any TopologicalEntity that uses any part of that larger physical/geographical unit will suffer impact and hence each TopologicalEntity shares risk.
                The identifier of each physical/geographical unit that is involved in the realization of each segment of a Topological entity can be listed in the RiskParameter_Pac of that TopologicalEntity.
                A segment has one or more risk characteristic.
                Shared risk between two TopologicalEntities compromises the integrity of any solution that use one of those TopologicalEntity as a backup for the other.
                Where two TopologicalEntities have a common risk characteristic they have an elevated probability of failing simultaneously compared to two TopologicalEntities that do not share risk characteristics.";
        }
        grouping transfer-capacity-pac {
            container total-potential-capacity {
                uses capacity;
                description "An optimistic view of the capacity of the TopologicalEntity assuming that any shared capacity is available to be taken.";
            }
            container available-capacity {
                uses capacity;
                description "Capacity available to be assigned.";
            }
            list capacity-assigned-to-user-view {
                key 'total-size maximum-usage-instances maximum-usage-size numbering-range';
                uses capacity;
                description "Capacity already assigned";
            }
            leaf capacity-interaction-algorithm {
                type string;
                description "A reference to an algorithm that describes how various chunks of allocated capacity interact (e.g. when shared)";
            }
            description "The TopologicalEntity derives capacity from the underlying realization. 
                A TopologicalEntity may be an abstraction and virtualization of a subset of the underlying capability offered in a view or may be directly reflecting the underlying realization.
                A TopologicalEntity may be directly used in the view or may be assigned to another view for use.
                The clients supported by a multi-layer TopologicalEntity may interact such that the resources used by one client may impact those available to another. This is derived from the LTP spec details.
                Represents the capacity available to user (client) along with client interaction and usage. 
                A TopologicalEntity may reflect one or more client protocols and one or more members for each profile.";
        }
        grouping transfer-cost-pac {
            list cost-characteristic {
                key 'cost-name cost-value cost-algorithm';
                uses cost-characteristic;
                description "The list of costs where each cost relates to some aspect of the TopologicalEntity.";
            }
            description "The cost characteristics of a TopologicalEntity not necessarily correlated to the cost of the underlying physical realization. 
                They may be quite specific to the individual TopologicalEntity e.g. opportunity cost. Relates to layer capacity
                There may be many perspectives from which cost may be considered  for a particular TopologicalEntity and hence many specific costs and potentially cost algorithms. 
                Using an entity will incur a cost. ";
        }
        grouping transfer-integrity-pac {
            leaf error-characteristic {
                type string;
                description "Describes the degree to which the signal propagated can be errored. 
                    Applies to TDM systems as the errored signal will be propagated and not packet as errored packets will be discarded.";
            }
            leaf loss-characteristic {
                type string;
                description "Describes the acceptable characteristic of lost packets where loss may result from discard due to errors or overflow.
                    Applies to packet systems and not TDM (as for TDM errored signals are propagated unless grossly errored and overflow/underflow turns into timing slips).";
            }
            leaf repeat-delivery-characteristic {
                type string;
                description "Primarily applies to packet systems where a packet may be delivered more than once (in fault recovery for example). 
                    It can also apply to TDM where several frames may be received twice due to switching in a system with a large differential propagation delay.";
            }
            leaf delivery-order-characteristic {
                type string;
                description "Describes the degree to which packets will be delivered out of sequence.
                    Does not apply to TDM as the TDM protocols maintain strict order.";
            }
            leaf unavailable-time-characteristic {
                type string;
                description "Describes the duration for which there may be no valid signal propagated.";
            }
            leaf server-integrity-process-characteristic {
                type string;
                description "Describes the effect of any server integrity enhancement process on the characteristics of the TopologicalEntity.";
            }
            description "Transfer intergrity characteristic covers expected/specified/acceptable characteristic of degradation of the transfered signal.
                It includes all aspects of possible degradation of signal content as well as any damage of any form to the total TopologicalEntity and to the carried signals.
                Note that the statement is of total impact to the TopologicalEntity so any partial usage of the TopologicalEntity (e.g. a signal that does not use full capacity) will only suffer its portion of the impact.";
        }
        grouping transfer-timing-pac {
            leaf fixed-latency-characteristic {
                type string;
                description "A TopologicalEntity suffers delay caused by the realization of the servers (e.g. distance related; FEC encoding etc.) along with some client specific processing. This is the total average latency effect of the TopologicalEntity";
            }
            leaf jitter-characteristic {
                type string;
                description "High frequency deviation from true periodicity of a signal and therefore a small high rate of change of transfer latency.
                    Applies to TDM systems (and not packet).";
            }
            leaf wander-characteristic {
                type string;
                description "Low frequency deviation from true periodicity of a signal and therefore a small low rate of change of transfer latency.
                    Applies to TDM systems (and not packet).";
            }
            list queuing-latency {
                key 'traffic-property-name latency-value';
                uses queuing-latency;
                description "The effect on the latency of a queuing process. This only has significant effect for packet based systems and has a complex characteristic.";
            }
            description "A TopologicalEntity will suffer effects from the underlying physical realization related to the timing of the information passed by the TopologicalEntity.";
        }
        grouping validation-pac {
            list validation-mechanism {
                key 'validation-mechanism layer-protocol-adjacency-validated validation-robustness';
                uses validation-mechanism;
                description "Provides details of the specific validation mechanism(s) used to confirm the presence of an intended topologicalEntity.";
            }
            description "Validation covers the various adjacenct discovery and reachability verification protocols. Also may cover Information source and degree of integrity.";
        }
        grouping te-link {
            leaf-list node {
                type leafref {
                    path '/net:network/net:node/net:node-id';
                }
                min-elements 2;
                max-elements 2;
                description "none";
            }
            leaf-list node-edge-point {
                type leafref {
                    path '/net:network/net:node/topo:termination-point/topo:tp-id';
                }
                max-elements 2;
                description "none";
            }
            uses tapi:local-class;
            description "The Link object class models effective adjacency between two or more ForwardingDomains (FD). ";
        }

    /***********************
    * package type-definitions
    **********************/ 
        grouping capacity {
            leaf total-size {
                type string;
                description "Total capacity of the TopologicalEntity in MB/s";
            }
            leaf maximum-usage-instances {
                type string;
                description "Where there is some limit to the number of client (e.g. in a channelized case).";
            }
            leaf maximum-usage-size {
                type string;
                description "Where a client is of variable capacity but due to some underlying realization the maximum size of the client is smaller than the totalSize.";
            }
            leaf numbering-range {
                type string;
                description "Method for identifying units of capacity via some numbering scheme.";
            }
            description "Information on capacity of a particular TopologicalEntity.";
        }
        grouping cost-characteristic {
            leaf cost-name {
                type string;
                description "The cost characteristic will related to some aspect of the TopologicalEntity (e.g. $ cost, routing weight). This aspect will be conveyed by the costName.";
            }
            leaf cost-value {
                type string;
                description "The specific cost.";
            }
            leaf cost-algorithm {
                type string;
                description "The cost may vary based upon some properties of the TopologicalEntity. The rules for the variation are conveyed by the costAlgorithm.";
            }
            description "The information for a particular cost characteristic.";
        }
        typedef fixed-capacity-value {
            type enumeration {
                enum not-applicable {
                    description "none";
                }
                enum 10mbps {
                    description "none";
                }
                enum 100mbps {
                    description "none";
                }
                enum 1gbps {
                    description "none";
                }
                enum 2.4gbps {
                    description "none";
                }
                enum 10gbps {
                    description "none";
                }
                enum 40gbps {
                    description "none";
                }
                enum 100gbps {
                    description "none";
                }
                enum 200gbps {
                    description "none";
                }
                enum 400gbps {
                    description "none";
                }
            }
            description "The Capacity (Bandwidth) values that are applicable for digital layers. ";
        }
        grouping queuing-latency {
            leaf traffic-property-name {
                type string;
                description "The identifier of the specific traffic property to which the queuing latency applies.";
            }
            leaf latency-value {
                type string;
                description "The specific queuing latency for the traffic property.";
            }
            description "Provides information on latency characteristic for a particular stated trafficProperty.";
        }
        grouping risk-characteristic {
            leaf risk-characteristic-name {
                type string;
                description "The name of the risk characteristic. The characteristic may be related to a specific degree of closeness. 
                    For example a particular characteristic may apply to failures that are localized (e.g. to one side of a road) where as another characteristic may relate to failures that have a broader impact (e.g. both sides of a road that crosses a bridge).
                    Depending upon the importance of the traffic being routed different risk characteristics will be evaluated.";
            }
            leaf-list risk-identifier-list {
                type string;
                min-elements 1;
                description "A list of the identifiers of each physical/geographic unit (with the specific risk characteristic) that is related to a segment of the TopologicalEntity.";
            }
            description "The information for a particular risk characteristic where there is a list of risk identifiers related to that characteristic.";
        }
        grouping validation-mechanism {
            leaf validation-mechanism {
                type string;
                description "Name of mechanism used to validate adjacency";
            }
            leaf layer-protocol-adjacency-validated {
                type string;
                description "State of validatiion";
            }
            leaf validation-robustness {
                type string;
                description "Quality of validation (i.e. how likely is the stated validation to be invalid)";
            }
            description "Identifies the validation mechanism and describes the characteristics of that mechanism";
        }
}
