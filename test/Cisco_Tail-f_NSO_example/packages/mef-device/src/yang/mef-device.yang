module mef-device {
  namespace "urn:mef:yang:mef-device";
  prefix mef-device;

  import ietf-yang-types {
    prefix yang;
  }
  import mef-device-types {
    prefix mef-types;
  }
   import mef-device-profiles {
        prefix mef-device-profiles;
    }
    import tapi {
        prefix tapi;
    }
    import ietf-network {
        prefix net;
    }
    import ietf-network-topology {
        prefix topo;
    }    
    import tapi-connectivity {
        prefix tapi-connectivity;
    }

  organization "Metro Ethernet Forum";
  contact
    "Web URL: http://metroethernetforum.org/
     E-mail:  mibs@metroethernetforum.org
     Postal:  Metro Ethernet Forum
              6033 W. Century Boulevard, Suite 1107
              Los Angeles, CA 90045
              U.S.A.
     Phone:   +1 310-642-2800
     Fax:     +1 310-642-2808";
  description
    "This module implements the Network Equipment (NE) side 
     EVC and UNI functionality specified 
     in MEF 10.3, MEF 6.2, and MEF 7.2.
     
     Reference Overview: 
     A number of base documents have been used to create 
     the MEF Device YANG Module. The following are the 
     abbreviations for the baseline documents:
     [RFC 6991] refers to IETF RFC 6991 'Common YANG Data Types',
     2013-07-15  
     [RFC 6643] refers to IETF RFC 6643 'Translation of Structure
     of Management Information
     Version 2 (SMIv2) MIB Modules to YANG Modules', 2011-11-25  
     [802.1AB] refers to 'Station and Media Access Control
     Connectivity Discovery', IEEE 802.1AB-2009, September 2009
     [802.1q] refers to IEEE 802.1Q-2011 'IEEE Standard for Local
     and metropolitan area networks --Media Access Control (MAC)
     Bridges and Virtual Bridged Local Area Networks, August 2011
     [802-2001] refers to 'IEEE Standard for Local and Metropolitan
     Area Networks: Overview and Architecture', IEEE 802-2001,
     February 2002
     [MEF10.3] refers to MEF 10.3 
     'Ethernet Services Attributes Phase 3', October 2013
     [MEF6.2] refers to MEF 6.2 
     'EVC Ethernet Services Defintions Phase 3', August 2014
     [MEF40] refers to MEF 40 
     'UNI and EVC Definition of Managed Objects', April 2013
     [MEF45] refers to MEF 45 'Multi-CEN L2CP', August 2014
     [MEF7.2] refers to MEF 7.2 
     'Carrier Ethernet Management Information Model', April 2013
     [MEF7.3] refers to MEF 7.3 
     'Carrier Ethernet Management Information Model',
     Working Draft #1 2015
     [RFC 2737] refers to IETF RFC 2737 'Entity MIB (Version 2)',
     December 1999
     [RFC 2863] refers to IETF RFC 2863 'The Interfaces Group MIB',
     June 2000
     [RFC 3419] refers to IETF RFC 3419 
     'Textual Conventions for Transport Addresses', December 2002
     [Y.1731] refers to ITU-T Y.1731 
     'OAM functions and mechanisms for Ethernet based networks',
     July 2011
     [Q.840.1] refers to ITU-T Q.840.1 
     'Requirements and analysis for NMS-EMS management interface
     of Ethernet over Transport and Metro Ethernet 
     Network(EoT/MEN)' March 2007";

  revision 2016-04-17 {
    description
      "First set of updates to better align with
       MEF Common Information Model names";
    reference "EVC Ethernet Services Definitions YANG Modules 
    	      (MEF XX), TBD";
  }

  revision 2015-06-26 {
    description
      "Empty Shell file created for discussion purposes.";
    reference "MEF Device YANG Module " +
    		"(MEF XX), TBD";
  }

 //   augment "/tapi-connectivity:connectivity-service" {
 //       uses cg-eth-conn-serv-spec;
 //       description "none";
 //   }
 //   augment "/tapi-connectivity:connectivity-service/tapi-connectivity:service-port" {
 //       uses cg-eth-frame-flow-cpa-aspec;
 //       description "none";
 //   }

//JB - I am starting with the concept that we are adding UNI Attributes to the termination points for a given node/device.
    augment "/net:network/net:node/topo:termination-point" {
        description
          "Add MEF UNI parameters to termination points in the IETF topology model.";
        //For Link aggregation, we set these for each physical link
        uses mef-uni-physical-layer-link-attrs; 
        //For Link Aggregation, we set the following for the UNI (aliased to Termination Point) which is at a high layer than the links
        uses mef-uni-end-point-attrs;
        //The list of EVC End Point Attributes that apply to each UNIs Configuration
        uses mef-evc-end-point-attrs;
      }   

    /* JB
     * 1. I have only considered the UNI list and EVC Flow Points in this first cut. 
     */
    
    grouping mef-uni-physical-layer-link-attrs {

        leaf ieee8023-phy {
            type identityref {
              base mef-types:ieee-8023-interface-type;
            }

            description
              "The Physical Layer for each physical link " +
              "implementing the UNI MUST be one of the " +
              "PHYs listed in IEEE Std 802.3–2012 but " +
              "excluding 1000BASE-PX-D and 1000BASE-PX-U.";
            reference "[MEF10.3] Section 9.2 [R60]";
          }
          leaf sync-mode {
            type boolean;

            default "false";
            description
              "Enabled or Disabled for each physical link " +
              "implementing the UNI.";
            reference "[MEF10.3] Section 9.3. [MEF6.2] " +
            		"Section 8.2.2. [MEF7.3] Section 10.2.2.";
          }
          leaf clock-accuracy {
            type decimal64 {
              fraction-digits 3;
            }
            units "ppm";
            description
              "ESMC:Ethernet Equipment Slave Clock Accuracy " +
              "in PPM. IEEE 802.3 standard specifies " +
              "that Ethernet clock accuracy is to be less " +
              "than or equal to +- 4.6 PPM.";
            reference "[MEF10.3] Section 9.3, [R62]. " +
            		"[MEF22.1], [IEEE802.3].";
          }
    }
    
    
    grouping mef-uni-end-point-attrs {
     
      container ce-vlans {
        description
          "Each UNI (Termination Point) MUST have list " +
          "of the CE-VLAN ID including mappings to configured " +
          "EVCs if assigned. This list of ce-vlans is a " +
          "complete list of all VLANs associated with this " +
          "UNI. At the Service Module level, there are two " +
          "lists: This one and the list of CE-VLAN IDs " +
          "associated with the EVC's UNI List as part of " +
          "the MEF Service Definition. ";
        reference "[MEF10.3] Section 9.10, [R77], [R78]. " +
        		"[MEF7.3] Section 10.2.2.";
        list ce-vlan {
          key "vid";
          description
            "A list of all EC-VLANs allowed ingres or egress " +
            "on the UNI. This is the UNI-specific CE-VLAN ID " +
            "listing as part of the Service Level " +
            "CE-VLAN ID / EVC Map.";
          reference "[MEF10.3] Section 9.10.1.";
          leaf vid {
            type mef-types:vlan-id-type;
            description
              "The Customer Edge VLAN ID is equivalent " +
              "to a Static VLAN allowed on that port " +
              "(ie. Port is not Forbidden). The " +
              "association with the EVC is part of " +
              "the EVC configuration.";
            reference "[MEF10.3] Section 9.10.";
          }
        }
      }
      container ingress-envelopes {
        presence "Ingress Bandwidth Profile Envelopes " +
        		"configured.";
        description
          "UNI Bandwidth Profile Flow Envelopes.";
        reference "[MEF10.3] Section 9.15, Section 12.1. " +
        		"[MEF6.2] Section 8.2.1: [R3]. " +
        		"[MEF7.3] Section 10.2.2.";
        list envelope {
          key "env-id";
          description
            "UNI Bandwidth Profile Flow Envelope List.";
          reference "[MEF10.3] Section 9.15, Section 12.1. " +
          		"[MEF6.2] Section 8.2.1, [R3], " +
          		"Section 8.2.2, [R4]. [MEF7.3] " +
          		"Section 10.2.2.";
          container bwp-flows {
            presence "Bandwidth Profile configured for " +
            		"this envelope.";
            description
              "UNI Bandwidth Profile Flows per Envelope.";
            reference "[MEF10.3] Section 12.1. " +
            		"[MEF6.2] Section 10.1.";
            list bwp-flow {
              key "bw-profile";
              ordered-by user;
              description
                "UNI Bandwidth Profile Flow List per Envelope. " +
                "The order of entries in the list is user " +
                "controlled. The first element of the list " +
                "has the lowest priority and the last " +
                "element will have the highest priority.";
              reference "[MEF10.3] Section 12.1. " +
              		"[MEF6.2] Section 10.1. " +
              		"[MEF6.2] Section 8.2.1, [R3]. ";
              leaf bw-profile {
                type leafref {
                  path "/mef-device-profiles:mef-device-profiles/mef-device-profiles:" +
                  		"profiles/mef-device-profiles:" +
                  		"ingress-bwp-flows/mef-device-profiles:" +
                  		"bwp-flow/mef-device-profiles:bw-profile";
                }
                description
                  "If no Ingress Bandwidth Profile per UNI " +
                  "has been defined (ie. 'No'), then the " +
                  "behavior has been defined at the Service " +
                  "Level of the configuration.";
                reference "[MEF10.3] Section 9.14, " +
                		"Section 12.1, [R84], [R134]. " +
                		"[MEF6.2] Section 8.2.1,[R3],[R136]. " +
                		"Section 8.2.2, 10.1, [R6]. [MEF7.3] " +
                		"Section 10.2.2.";
              }
            }
          }
          leaf env-id {
            type mef-types:identifier45;
            description
              "This attribute identifies the Envelope of " +
              "Bandwidth Profile Parameters.";
            reference "[MEF10.3] Section 12.1.";
          }
          leaf coupling-enabled {
            type boolean;
            default "false";
            description
              "The Envelope Coupling Flag (CF) attribute.";
            reference "[MEF10.3] Section 12.1.";
          }
        }
      }
      container egress-envelopes {
        presence "Egress Bandwidth Profile Envelopes configured.";
        description
          "UNI Bandwidth Profile Flow Envelopes.";
        reference "[MEF10.3] Section 9.15, Section 12.1. " +
        		"[MEF6.2] Section 8.2.1: [R3]. " +
        		"[MEF7.3] Section 10.2.2.";
        list envelope {
          key "env-id";
          description
            "UNI Bandwidth Profile Flow Envelope List.";
          reference "[MEF10.3] Section 9.15, Section 12.1. " +
          		"[MEF6.2] Section 8.2.1, [R3], " +
          		"Section 8.2.2, [R4]. [MEF7.3] " +
          		"Section 10.2.2.";
          container bwp-flows {
            presence "Bandwidth Profile configured for " +
            		"this envelope.";
            description
              "UNI Bandwidth Profile Flows per Envelope.";
            reference "[MEF10.3] Section 12.1. [MEF6.2] " +
            		"Section 10.1.";
            list bwp-flow {
              key "bw-profile";
              ordered-by user;
              description
                "UNI Bandwidth Profile Flow List per Envelope. " +
                "The order of entries in the list is user " +
                "controlled. The first element of the list " +
                "has the lowest priority and the last element " +
                "will have the highest priority.";
              reference "[MEF10.3] Section 12.1. " +
              		"[MEF6.2] Section 10.1. " +
              		"[MEF6.2] Section 8.2.1, [R3]. ";
              leaf bw-profile {
                type leafref {
                  path "/mef-device-profiles:mef-device-profiles/mef-device-profiles:" +
                  		"profiles/mef-device-profiles:egress-bwp-flows" +
                  		"/mef-device-profiles:bwp-flow/" +
                  		"mef-device-profiles:bw-profile";
                }
                description
                  "UNI Bandwidth Profile Flow per Envelope.";
                reference "[MEF10.3] Section 12.1. " +
                		"[MEF6.2] Section 10.1. " +
                		"[MEF6.2] Section 8.2.1, [R3], [R136]. ";
              }
            }
          }
          leaf env-id {
            type mef-types:identifier45;
            description
              "This attribute identifies the Envelope of " +
              "Bandwidth Profile Parameters.";
            reference "[MEF10.3] Section 12.1.";
          }
          leaf coupling-enabled {
            type boolean;
            default "false";
            description
              "The Envelope Coupling Flag (CF) attribute.";
            reference "[MEF10.3] Section 12.1.";
          }
        }
      }
      container status {
        description
          "This group is related to the MEF 7.3 External " +
          "Network Interface";
        leaf operational-state {
          type boolean;
          default "false";
          config false;
          description
            "Operational Status of the Link as " +
            "Enabled/Disabled.";
          reference "[MEF15]. [MEF7.3] Section 10.1.1.";
        }
        leaf number-of-links {
          type uint32;
          default "0";
          config false;
          description
            "A count of the number of physical links in this " +
            "physical layer.";
          reference "[MEF15]. [MEF7.3] Section 10.1.1.";
        }
      }
      leaf admin-state {
        type boolean;
        default "true";
        description
          "Locked/Unlocked is inconsistent with Oper Status " +
          "and will be confusing.";
        reference "MEF 15. MEF 7.3 Section 10.1.1.";
      }
      leaf mac-address {
        type yang:mac-address;
        description
          "MAC Address.";
        reference "[MEF15]. [MEF7.3] Section 10.1.1.";
      }
      leaf link-aggregation {
        type mef-types:link-aggregation-type;
        default "none";
        description
          "UNI Resiliency.";
        reference "[MEF10.3] Section 9.5 [R64], [R65], [R66], " +
        		"[R67]. [MEF6.2] Section 8.2.2.";
      }
      leaf max-svc-frame-size {
        type mef-types:max-svc-frame-size-type;
        default "1600";
        description
          "This attribute describes the maximum service frame " +
          "size for the UNI.";
        reference "[MEF10.3] Section 9.7, [R71], MEF 6.2 " +
        		"Section 8.2.2 and MEF 22.1: [D2]. " +
        		"[MEF7.3] Section 10.2.2.";
      }
      leaf service-multiplexing-enabled {
        type boolean;
        default "false";
        description
          "Service Multiplexing Enable - Enable if to support " +
          "multiple EVCs per UNI.";
        reference "[MEF10.3] Section 9.8. " +
        		"[MEF7.3] Section 10.2.2.";
      }
      leaf bundling-enabled {
        type boolean;
        default "false";
        description
          "When a UNI has Bundling Enabled, it MUST be able to " +
          "support more than one CE-VLAN ID mapping to a " +
          "particular EVC at the UNI.  When more than one " +
          "CE-VLAN-ID is mapped to an EVC at a UNI, the " +
          "EVC have CE-VLAN ID Preservation enabled";
        reference "[MEF10.3] Section 9.12, [R25], [R77], " +
        		"[R78], [R80]. [MEF7.3] Section 10.2.2.";
      }
      leaf all-to-one-bundling-enabled {
        type boolean;
        default "false";
        description
          "When all-to-one-bundling-enabled = true, all " +
          "CE-VLAN IDs MUST map to a single EVC at the " +
          "UNI. This also means that the UNI cannot " +
          "have service-multiplexing-enabled = true. When " +
          "all-to-one-bundling-enabled = true, " +
          "all other UNIs in the EVC associating this UNI " +
          "must have all-to-one-bundling-enabled = true. " +
          "If this values is true, the value of " +
          "untagged-and-priority-tagged-ce-vlan-id is not " +
          "applicable.";
        reference "[MEF10.3] Section 9.13, Table 12 " +
        		"(5 valid combinations), [R82], [R83]. " +
        		"[MEF7.3] Section 10.2.2.";
      }
      leaf untagged-and-priority-tagged-ce-vlan-id {
        type mef-types:vlan-id-type;
        default "1";
        description
          "The untagged-and-priority-tagged-ce-vlan-id is " +
          "equivalent to the Layer 2 PVID (Port VLAN ID) " +
          "with the Q-BRIDGE-MIB option for frame admitance set " +
          "to admitAll. With AdmitAll set, all Untagged and " +
          "Priority Tagged Service Frames are treated with " +
          "the CE-VLAN-ID tag on ingress. It is not applicable " +
          "if All in One Bundling is enabled.";
        reference "[MEF10.3] Section 9.9, [R73], [R74], " +
        		"[R75]. [MEF7.3] Section 10.2.2.";
      }
      leaf token-share-enabled {
        type boolean;
        default "false";
        description
          "Token Share Enabled/Disabled is used to indicate " +
          "whether a given UNI is capable of sharing tokens " +
          "across Bandwidth Profile Flows in an envelope.";
        reference "[MEF6.2] Section 8.2.1, [R2], [D1], [R3]. " +
        		"[MEF7.3] Section 10.2.2.";
      }
      leaf ingress-bw-profile-per-uni {
        type leafref {
          path "/mef-device-profiles:mef-device-profiles/mef-device-profiles:profiles/" +
          		"mef-device-profiles:ingress-bwp-flows/mef-device-profiles:" +
          		"bwp-flow/mef-device-profiles:bw-profile";
        }
        description
          "Ingress Bandwidth Profile for this UNI.";
        reference "[MEF10.3] Section 9.15, Section 12.1. " +
        		"[MEF6.2] Section 8.2.1: [R3]. " +
        		"[MEF7.3] Section 10.2.2.";
      }
      leaf egress-bw-profile-per-uni {
        type leafref {
          path "/mef-device-profiles:mef-device-profiles/mef-device-profiles:profiles/" +
          		"mef-device-profiles:egress-bwp-flows/mef-device-profiles:" +
          		"bwp-flow/mef-device-profiles:bw-profile";
        }
        description
          "Egress Bandwidth Profile Flow for this UNI.";
        reference "[MEF10.3] Section 9.15, Section 12.1. " +
        		"[MEF6.2] Section 8.2.1: [R3]. " +
        		"[MEF7.3] Section 10.2.2.";
      }
      leaf link-oam-enabled {
        type boolean;
        default "false";
        description
          "Link OAM Enabled/Disabled.";
        reference "[MEF10.3] Section 9.16, [R86]. " +
        		"[MEF6.2] Section 8.2.2, [D3]. " +
        		"[MEF7.3] Section 10.2.2.";
      }
      leaf uni-meg-enabled {
        type boolean;
        default "false";
        description
          "Enables / Disables the Maintenance Entity Group (MEG).";
        reference "[MEF10.3] Section 9.17, [R87]. " +
        		"[MEF30.1] Section 7.9. [MEF6.2] Section 8.2.2, " +
        		"[D4]. [MEF7.3] Section 10.2.2.";
      }
      leaf elmi-enabled {
        type boolean;
        must "(. = 'false') or " +
        		"(. = 'true' and " +
        		"(../elmi-profile))" {
          error-message "ELMI Profile must be set if " +
          		"ELMI is Enabled.";
          description
            "Ethernet Local Management Interface(ELMI) " +
            "Profile ID must be set if ELMI is Enabled.";
        }
        default "false";
        description
          "Ethernet Local Management Interface(ELMI) " +
          "Enabled / Disabled.";
        reference "[MEF10.3] Section 9.18, [R88]. " +
        		"[MEF16]. [MEF6.2] Section 8.2.2, [D5]. " +
        		"[MEF7.3] Section 10.2.2.";
      }
      leaf elmi-profile {
        type leafref {
          path "/mef-device-profiles:mef-device-profiles/mef-device-profiles:profiles/" +
          		"mef-device-profiles:elmi/mef-device-profiles:elmi-profile/" +
          		"mef-device-profiles:id";
        }
        description
          "The ELMI Profile is only applicable when ELMI " +
          "is enabled. The E-LMI protocol is based on " +
          "ITU-T Q.933, X.36 and other relevant " +
          "recommendations as well as Frame Relay " +
          "Local Management Interface (FR-LMI) " +
          "Implementation Agreement document defined " +
          "by the Frame Relay Forum and related " +
          "ITU-T recommendations.";
        reference "[MEF10.3] Section 9.18. " +
        		"[MEF7.3] Section 10.2.2.";
      }
      leaf l2cp-address-set {
        type mef-types:l2cp-address-set-type;
        default "cta";
        description
          "The L2CP Address Set Service Attribute specifies " +
          "the subset of the Bridge Reserved Addresses " +
          "that are filtered (i.e. L2CP Frames with " +
          "this destination address are Peered or " +
          "Discarded but not Passed) at a L2CP Decision Point.";
        reference "[MEF10.3] Section 9.19. " +
        		"[MEF45] Section 8.1, [R2] through [R9]. " +
        		"[MEF6.2] Section 8.2.2, [R1]. " +
        		"[MEF45] Section 8.1.";
      }
      leaf l2cp-peering {
        type leafref {
          path "/mef-device-profiles:mef-device-profiles/mef-device-profiles:profiles/" +
          		"mef-device-profiles:l2cp-peering/mef-device-profiles:" +
          		"l2cp-profile/mef-device-profiles:id";
        }
        description
          "L2CP Peering Profile for this UNI. This profile " +
          "may contain groups of L2CP Destination " +
          "MAC Addresses and protocols to be peered at " +
          "the UNI (as opposed to being passed or discarded).";
        reference "[MEF10.3] Section 9.19. " +
        		"[MEF45] Section 8.2. " +
        		"[MEF7.3] Section 10.2.2.";
      }   	
    }

    
  grouping mef-evc-end-point-attrs {
	  
      container ingress-bwp-flows-per-cos {
          presence "Use Ingress Bandwidth Profiles Per CoS";
          description
            "EVC Per UNI Class of Service Identifiers " +
            "corresponding to this EVC's Ingress Bandwidth " +
            "Profile Flows.";
          leaf coupling-enabled {
            type boolean;
            default "false";
            description
              "EVC Per UNI Envelope Coupling Flag (CF) " +
              "attribute.";
            reference "[MEF10.3] Section 12.1.";
          }
          list bwp-flow-per-cos {
            key "cos-name";
            description
              "EVC Per UNI: The list of Class of " +
              "Service Identifiers corresponding to " +
              "this UNI's Ingress Bandwidth Profile Flow.";
            leaf cos-name {
              type leafref {
                path "/mef-device-profiles:mef-device-profiles/mef-device-profiles:" +
                		"profiles/mef-device-profiles:cos-names/" +
                		"mef-device-profiles:cos-name/mef-device-profiles:name";
              }
              description
                "EVC Per UNI: Class of Service Identifier " +
                "for this Bandwidth Profile Flow.";
              reference "[MEF7.3] Section 12.1.2.";
            }
 /*  JB need to think more on BW Abstraction         
            leaf bw-profile {
              type leafref {
                path "/mef-interfaces:mef-interfaces/" +
                		"mef-interfaces:unis/mef-interfaces:" +
                		"uni[mef-interfaces:uni-id = " +
                		"current()/../../../uni-id]/" +
                		"mef-interfaces:ingress-envelopes/" +
                		"mef-interfaces:envelope/mef-interfaces:" +
                		"env-id";
              }
              mandatory true;
              description
                "EVC Per UNI: Ingress Bandwidth Profile " +
                "Envelope Per CoS ID. If this parameter " +
                "is not configured (ie. 'No') this setting " +
                "is configured else at the UNI Level.";
              reference "[MEF10.3] Section 10.6, Table 28. " +
              		"[MEF7.3] Section 12.1.2.";
            }
*/
          }
        }
        container egress-bwp-flows-per-eec {
          presence "Using Egress Bandwidth Profiles Per Egress" +
          		" Equivalence Class";
          description
            "EVC Per UNI: The Egress Equivalence Class " +
            "Identifiers corresponding to this EVC's " +
            "Egress Bandwidth Profile Flows.";
          leaf coupling-enabled {
            type boolean;
            default "false";
            description
              "EVC Per UNI: The Envelope Coupling Flag " +
              "(CF) attribute.";
            reference "[MEF10.3] Section 12.1.";
          }
          list bwp-flow-per-eec {
            key "eec-name";
            description
              "EVC Per UNI: The list of Egress Equivalence " +
              "Class Identifiers corresponding to this EVC's " +
              "Egress Bandwidth Profile Flow.";
            leaf eec-name {
              type leafref {
                path "/mef-device-profiles:mef-device-profiles/mef-device-profiles:" +
                		"profiles/mef-device-profiles:eec-names/" +
                		"mef-device-profiles:eec-name/mef-device-profiles:name";
              }
              description
                "EVC Per UNI: Egress Equivalence Class " +
                "Identifier for this Bandwidth Profile Flow.";
              reference "[MEF7.3] Section 12.1.2.";
            }
   /*  JB need to think more on BW Abstraction            
            leaf bw-profile {
              type leafref {
                path "/mef-interfaces:mef-interfaces/" +
                		"mef-interfaces:unis/mef-interfaces:" +
                		"uni[mef-interfaces:uni-id = " +
                		"current()/../../../uni-id]" +
                		"/mef-interfaces:" +
                		"egress-envelopes/" +
                		"mef-interfaces:envelope/" +
                		"mef-interfaces:env-id";
              }
              mandatory true;
              description
                "EVC Per UNI: Egress Bandwidth Profile " +
                "Envelope Per Equivance Class. " +
                "If this parameter is not configured " +
                "(ie. 'No') this setting is configured " +
                "else at the UNI Level.";
              reference "[MEF10.3] Section 10.6, " +
              		"Table 28. [MEF7.3] Section 12.1.2.";
            }
  */          
          }
        }

        leaf role {
          type mef-types:evc-uni-role-type;
          mandatory false;
          description
            "EVC Per UNI: The UNI Role MUST have the value " +
            "of either 'root' or 'leaf'.";
          reference "[MEF10.3] [R4], [R5], [R10], [R11]," +
          		" [R12]. [MEF7.3] Section 12.2.2.";
        }
        leaf color-identifier {
          type mef-types:cos-color-identifier-type;
          description
            "EVC Per UNI: The Color Identifier for Service " +
            "Frames.";
          reference "[MEF10.3] Section 10.3. " +
          		"[MEF7.3] Section 12.1.2.";
        }
        leaf cos-identifier {
          type leafref {
            path "/mef-device-profiles:mef-device-profiles/mef-device-profiles:" +
            		"profiles/mef-device-profiles:cos/mef-device-profiles:" +
            		"cos-profile/mef-device-profiles:id";
          }
          description
            "EVC Per UNI: Ingress Data Service Frame " +
            "CoS Profile.";
          reference "[MEF10.3] Section 8.8, Section 10.2. " +
          		"[MEF7.3] Section 12.1.2.";
        }
        leaf eec-identifier {
          type leafref {
            path "/mef-device-profiles:mef-device-profiles/mef-device-profiles:profiles" +
            		"/mef-device-profiles:eec/mef-device-profiles:eec-profile" +
            		"/mef-device-profiles:id";
          }
          description
            "EVC Per UNI: Egress Data Service Frame " +
            "Processing.";
          reference "[MEF10.3] Section 10.4." +
          		" [MEF7.3] Section 12.1.2.";
        }
  /*  JB need to think more on BW Abstraction       
        leaf ingress-bw-profile-per-evc {
          type leafref {
            path "/mef-interfaces:mef-interfaces/" +
            		"mef-interfaces:unis/mef-interfaces:uni" +
            		"[mef-interfaces:uni-id = current()/../" +
            		"uni-id]/mef-interfaces:ingress-envelopes" +
            		"/mef-interfaces:envelope/" +
            		"mef-interfaces:env-id";
          }
          description
            "EVC Per UNI: Ingress Bandwidth Profile " +
            "Envelope Per EVC. If this parameter is " +
            "not configured (ie. 'No') this setting is " +
            "configured else at the UNI Level.";
          reference "[MEF10.3] Section 10.5. " +
          		"[MEF7.3] Section 12.1.2.";
        }
 */
 /*  JB need to think more on BW Abstraction
        leaf egress-bw-profile-per-evc {
          type leafref {
            path "/mef-interfaces:mef-interfaces/" +
            		"mef-interfaces:unis/mef-interfaces:" +
            		"uni[mef-interfaces:uni-id = " +
            		"current()/../uni-id]/mef-interfaces:" +
            		"egress-envelopes/mef-interfaces:" +
            		"envelope/mef-interfaces:env-id";
          }
          description
            "EVC Per UNI: Egress Bandwidth Profile Envelope " +
            "Per EVC. If this parameter is not configured " +
            "(ie. 'No') this setting is configured else " +
            "at the UNI Level.";
          reference "[MEF10.3] Section 10.7. " +
          		"[MEF7.3] Section 12.1.2.";
        }
  */
        leaf source-mac-address-limit-enabled {
          type boolean;
          default "false";
          description
            "EVC Per UNI: Source MAC Address Limit " +
            "Enable / Disable. If Enabled, the values" +
            " for the Source MAC Address Limit and " +
            "Source MAC Address Interval must be set.";
          reference "[MEF10.3] Section 10.9. " +
          		"[MEF7.3] Section 12.1.2.";
        }
        leaf source-mac-address-limit {
          type uint32 {
            range "1..max";
          }
          description
            "EVC Per UNI: Source MAC Address Limit. " +
            "This value is used when the Source MAC " +
            "Address Limit Enabled is true.";
          reference "[MEF10.3] Section 10.9.";
        }
        leaf source-mac-address-limit-time-interval {
          type yang:timeticks;
          default "0";
          description
            "EVC Per UNI: Source MAC Address Limit Interval. " +
            "This value is used when the Source MAC Address " +
            "Limit Enabled is true.";
          reference "[MEF10.3] Section 10.9.";
        }
        leaf test-meg-enabled {
          type boolean;
          default "false";
          description
            "EVC Per UNI: Test MEG Enabled / Disabled.";
          reference "[MEF10.3] Section 10.10. " +
          		"[MEF7.3] Section 12.1.2.";
        }
        leaf subscriber-meg-mip-enabled {
          type boolean;
          default "false";
          description
            "EVC Per UNI: Subscriber MEG MIP Enabled / " +
            "Disabled.";
          reference "[MEF10.3] Section 10.11. " +
          		"[MEF7.3] Section 12.1.2.";
        }	  
  }  

}
