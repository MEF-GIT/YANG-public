module mef-global {
  namespace "urn:mef:yang:mef-global";
  prefix mef-global;

  import ietf-yang-types {
    prefix yang;
  }
  import ietf-inet-types {
    prefix inet;
  }
  import mef-types {
    prefix mef-types;
  }

  organization "Metro Ethernet Forum";
  contact
    "Web URL: http://metroethernetforum.org/
     E-mail:  mibs@metroethernetforum.org
     Postal:  Metro Ethernet Forum
              6033 W. Century Boulevard, Suite 1107
              Los Angeles, CA 90045
              U.S.A.
     Phone:   +1 310-642-2800
     Fax:     +1 310-642-2808";
  description
    "This module defines the shared profiles and related lists 
     to be referenced when configuring MEF Services. Service 
     Providers are expected to define a set of profiles for 
     Service Attributes associated with Bandwidth, L2CP, CoS, 
     and so on. These are expected to be slowly changing as 
     they reflect the Products offered by the Service Providers 
     to their Subscribers.
     
     Reference Overview:
     A number of base documents have been used to create 
     the MEF Global YANG Module. The following are the 
     abbreviations for the baseline documents:
     [RFC 6991] refers to IETF RFC 6991 'Common YANG Data Types',
     2013-07-15  
     [RFC 6643] refers to IETF RFC 6643 'Translation of Structure
     of Management Information
     Version 2 (SMIv2) MIB Modules to YANG Modules', 2011-11-25  
     [802.1AB] refers to 'Station and Media Access Control
     Connectivity Discovery', IEEE 802.1AB-2009, September 2009
     [802.1q] refers to IEEE 802.1Q-2011 'IEEE Standard for Local
     and metropolitan area networks --Media Access Control (MAC)
     Bridges and Virtual Bridged Local Area Networks, August 2011
     [802-2001] refers to 'IEEE Standard for Local and Metropolitan
     Area Networks: Overview and Architecture', IEEE 802-2001,
     February 2002
     [MEF10.3] refers to MEF 10.3 
     'Ethernet Services Attributes Phase 3', October 2013
     [MEF6.2] refers to MEF 6.2 
     'EVC Ethernet Services Defintions Phase 3', August 2014
     [MEF40] refers to MEF 40 
     'UNI and EVC Definition of Managed Objects', April 2013
     [MEF45] refers to MEF 45 'Multi-CEN L2CP', August 2014
     [MEF7.2] refers to MEF 7.2 
     'Carrier Ethernet Management Information Model', April 2013
     [MEF7.3] refers to MEF 7.3 
     'Carrier Ethernet Management Information Model',
     Working Draft #1 2015
     [RFC 2737] refers to IETF RFC 2737 'Entity MIB (Version 2)',
     December 1999
     [RFC 2863] refers to IETF RFC 2863 'The Interfaces Group MIB',
     June 2000
     [RFC 3419] refers to IETF RFC 3419 
     'Textual Conventions for Transport Addresses', December 2002
     [Y.1731] refers to ITU-T Y.1731 
     'OAM functions and mechanisms for Ethernet based networks',
     July 2011
     [Q.840.1] refers to ITU-T Q.840.1 
     'Requirements and analysis for NMS-EMS management interface
     of Ethernet over Transport and Metro Ethernet 
     Network(EoT/MEN)' March 2007";

  revision 2017-01-10 {
    description
      "Updated to address CFC1 Review Comments.";
    reference
      "EVC Ethernet Services Definitions YANG Modules 
       (MEF XX), TBD";
  }
  revision 2016-04-17 {
    description
      "First set of updates to better align with
       MEF Common Information Model names";
    reference
      "EVC Ethernet Services Definitions YANG Modules 
       (MEF XX), TBD";
  }
  revision 2015-05-26 {
    description
      "Formal Project Review Draft 1.";
    reference
      "EVC Ethernet Services Definitions YANG Modules 
       (MEF XX), TBD";
  }

  container mef-global {
    description
      "MEF Global Profiles";

    grouping bwp-flows-parameter-set-group {
      description
        "Bandwidth Profile Flows Group.";
      list bwp-flow-parameter-set {
        key "bwp-flow-parameter-set-id";
        description
          "Bandwidth Profiles.";
        reference "[MEF10.3] Section 9.14, 12.2.";
        leaf bwp-flow-parameter-set-id {
          type mef-types:identifier255;
          description
            "Bandwidth Profile Identifier.";
          reference "[MEF10.3] Section 9.14, 12.2.";
        }
        leaf cir {
          type mef-types:bwp-ir-type;
          units "bits-per-sec";
          default "0";
          description
            "This attribute identifies the Committed Information Rate (CIR) in bits per second for one BWP flow. If the value is 0, then no guarantee is assumed.";
        }
        leaf cir-max {
          type mef-types:bwp-ir-type;
          units "bits-per-sec";
          default "0";
          description
            "This attribute identifies the Maximum Committed Information Rate (CIR). This parameter limits the rate of tokens added to the committed token bucket. If this value is 0, then no limit is assumed.";
        }
        leaf cbs {
          type mef-types:bwp-bs-type;
          units "bytes";
          default "0";
          description
            "This attribute identifies the Committed Burst Size (CBS) in bytes for one BWP flow. This parameter limits the maximum number of bytes available for a burst of Service Frames sent at the UNI line rate that will be declared Green by the Bandwidth Profile. If this value is 0, then no limit is assumed.";
        }
        leaf eir {
          type mef-types:bwp-ir-type;
          units "bits-per-sec";
          default "0";
          description
            "This attribute identifies the Excess Information Rate (EIR) in bits per second for one BWP flow.  This parameter limits the average rate in bits per second of Service Frames that will be declared Yellow by the Bandwidth Profile. If this value is 0, then no limit is assumed.";
        }
        leaf eir-max {
          type mef-types:bwp-ir-type;
          units "bits-per-sec";
          default "0";
          description
            "This attribute identifies the Maximum Excess Information Rate (EIR) in bits per second for one BWP flow. This parameter limits the rate of tokens added to the excess token bucket. If this value is 0, then no limit is assumed.";
        }
        leaf ebs {
          type mef-types:bwp-bs-type;
          units "bytes";
          default "0";
          description
            "This attribute identifies the Excess Burst Size (EBS) in bytes for one BWP flow. This parameter limits the maximum number of bytes available for a burst of Service Frames sent at the UNI line rate that will be declared Yellow by the Bandwidth Profile. If this value is 0, then no limit is assumed.";
        }
        leaf coupling-enabled {
          type boolean;
          default "false";
          description
            "The Per Bandwidth Profile Coupling Flag (CF) attribute. This parameter determines whether or not overflow tokens not used for Service Frames declared Green can be used as Yellow tokens.";
          reference "[MEF10.3] Section 12.1 [R149].";
        }
        leaf color-mode {
          type mef-types:bwp-color-mode-type;
          default "color-blind";
          description
            "This attribute describes the color mode (CM) to be applied as 'color-blind mode' or 'color-aware mode'.";
          reference "[MEF10.3] Section 10.3, [R151].";
        }
        leaf coupling-flag {
          type mef-types:bwp-coupling-flag-type;
          default "false";
          description
            "The optional coupling flag (CF) attribute, describes if yellow frames will be admitted if unused bandwidth is available. When CF is set to false (\"yellow-eir-only\"), the volume of the yellow service frames admitted to the network cannot exceed EIR. When CF is set to \"yellow-eir-plus-cir\", the volume of the yellow service frames admitted to the network is bounded by CIR + EIR depending on volume of the offered green Service Frames. In both cases the burst size of the yellow service frames admitted to the network is bounded by EBS.";
          reference "[MEF10.3] Section 12.1.";
        }
      }
    }
    container sls-profiles {
      description
        "The technical specification of the service level being offered by the Service Provider to the Subscriber is defined to be the Service Level Specification (SLS).";
      list sls-profile {
        key "sls-id";
        description
          "Global Service Level Specification(SLS) List.";
        leaf sls-id {
          type mef-types:sls-type;
          description
            "The SLS ID identifies a specific Service Level Specification offered by a Service Provider.";
          reference "[MEF10.3] Section 8.8. The SLS ID must be unique for this Service Provider.";
        }
        leaf time-interval {
          type uint64;
          units "seconds";
          mandatory true;
          description
            "Performance Metric(PM): Time Interval (seconds).";
        }
        container pm-cos-name-entries {
          description
            "Performance Metrics for this SLS.";
          list pm-cos-name-entry {
            key "cos-name";
            description
              "List of Performance Metrics based SLS entries by Class of Service Names";
            leaf cos-name {
              type leafref {
                path "/mef-global:mef-global/profiles/cos-names/cos-name/name";
              }
              description
                "CoS Name Identifier.";
            }
            leaf delta-t {
              type uint64;
              units "ms";
              mandatory true;
              description
                "A time interval much smaller than pm-time-interval.";
            }
            leaf threshold-c {
              type mef-types:simple-percent;
              units "percent";
              mandatory true;
              description
                "Unavailability frame loss ratio threshold expressed in percentage.";
            }
            leaf consecutive-interval-n {
              type uint8;
              mandatory true;
              description
                "Number of consecutive small time intervals to assess.";
            }
            container pm-entries {
              description
                "Performance Metrics for this SLS.";
              list pm-entry {
                key "pm-entry-id";
                description
                  "For any given SLS, performance objectives related to the Performance Metrics may or may not be specified. No functionally duplicated Performance Objectives are allowed.";
                leaf pm-entry-id {
                  type mef-types:identifier45;
                  description
                    "This is a friendly name for specific performance profile.";
                }
                choice one-way-performance-metric {
                  description
                    "Choice of different One-Way Performance Objectives";
                  mandatory true;
                  case fd {
                    container one-way-frame-delay-pm {
                      description
                        "one-way-frame-delay-pm";
                      leaf percentile {
                        type mef-types:simple-percent;
                        units "percent";
                        mandatory true;
                        description
                          "Frame Delay Performance Percentile.";
                      }
                      leaf objective {
                        type uint64;
                        units "ms";
                        mandatory true;
                        description
                          "Frame Delay Performance Objective.";
                      }
                    }
                  }
                  case mfd {
                    container one-way-mean-frame-delay-pm {
                      description
                        "one-way-mean-frame-delay-pm";
                      leaf objective {
                        type uint64;
                        units "ms";
                        mandatory true;
                        description
                          "Frame Delay Mean Performance Objective.";
                      }
                    }
                  }
                  case fdr {
                    container one-way-frame-delay-range-pm {
                      description
                        "one-way-frame-delay-range-pm";
                      leaf percentile {
                        type mef-types:simple-percent;
                        units "percent";
                        mandatory true;
                        description
                          "Frame Delay Range Performance Percentile.";
                      }
                      leaf objective {
                        type uint64;
                        units "ms";
                        mandatory true;
                        description
                          "Frame Delay Range Performance Objective.";
                      }
                    }
                  }
                  case ifdv {
                    container one-way-inter-frame-delay-variation-pm {
                      description
                        "one-way-inter-frame-delay-variation-pm";
                      leaf percentile {
                        type mef-types:simple-percent;
                        units "percent";
                        mandatory true;
                        description
                          "Inter-Frame Delay VariationPerformance Percentile.";
                      }
                      leaf frame-pair-separation {
                        type uint64;
                        units "ms";
                        mandatory true;
                        description
                          "Inter-Frame Delay VariationPerformance Separation / Pair Interval.";
                      }
                      leaf objective {
                        type uint64;
                        units "ms";
                        mandatory true;
                        description
                          "Inter-Frame Delay Variation Performance Objective.";
                      }
                    }
                  }
                  case flr {
                    container one-way-frame-loss-ratio-pm {
                      description
                        "one-way-frame-loss-ratio-pm";
                      leaf percentile {
                        type mef-types:simple-percent;
                        units "percent";
                        mandatory true;
                        description
                          "Frame Loss Ratio Performance Objective (Percentile).";
                      }
                    }
                  }
                  case availability {
                    container one-way-availability-pm {
                      description
                        "one-way-availability-pm";
                      leaf percentile {
                        type mef-types:simple-percent;
                        units "percent";
                        mandatory true;
                        description
                          "Availability Performance Metric Objective (Percentile)";
                      }
                    }
                  }
                  case hli {
                    container one-way-high-loss-interval-pm {
                      description
                        "one-way-high-loss-interval-pm";
                      leaf objective {
                        type uint64;
                        mandatory true;
                        description
                          "HLI Performance Objective expressed as an integer.";
                      }
                    }
                  }
                  case chli {
                    container one-way-consecutive-high-loss-interval-pm {
                      description
                        "one-way-consecutive-high-loss-interval-pm";
                      leaf consecutive-number-p {
                        type uint64;
                        must ". < ../../../../consecutive-interval-n" {
                          error-message "The value of chli-consecutive-small-time-intervals must be less than consecutive-small-time-intervals (where p < n) if both are defined.";
                          description
                            "The value of chli-consecutive-small-time-intervals must be less than consecutive-small-time-intervals (where p < n) if both are defined.";
                          reference "[MEF 10.3].";
                        }
                        mandatory true;
                        description
                          "Number of consecutive small time intervals for assessing CHLI.";
                        reference "[MEF10.3] Table 10.";
                      }
                      leaf objective {
                        type uint64;
                        mandatory true;
                        description
                          "Consecutive HLI Performance Objective expressed as an integer.";
                      }
                    }
                  }
                  case cpm {
                    container one-way-composite-pm {
                      description
                        "one-way-composite-pm";
                      leaf cpi-threshold-u {
                        type mef-types:simple-percent;
                        units "percent";
                        mandatory true;
                        description
                          "cpi-threshold-u";
                      }
                      leaf frame-loss-indicator {
                        type boolean;
                        mandatory true;
                        description
                          "frame-loss-indicator";
                      }
                      leaf frame-delay-indicator {
                        type boolean;
                        mandatory true;
                        description
                          "frame-delay-indicator";
                      }
                      leaf ifdv-indicator {
                        type boolean;
                        mandatory true;
                        description
                          "ifdv-indicator";
                      }
                      leaf one-way-fd-threshold {
                        type uint64;
                        mandatory true;
                        description
                          "one-way-fd-threshold";
                      }
                      leaf one-way-ifdv-threshold {
                        type uint64;
                        mandatory true;
                        description
                          "one-way-ifdv-threshold";
                      }
                      leaf objective {
                        type uint64;
                        mandatory true;
                        description
                          "Composite Performance Metric Objective";
                      }
                    }
                  }
                  case group-avail {
                    container one-way-group-availability-pm {
                      description
                        "one-way-group-availability-pm";
                      leaf min-number-of-uni-pair-sets {
                        type uint64;
                        mandatory true;
                        description
                          "Minimum number of sets of ordered UNI pairs.";
                      }
                      leaf objective {
                        type uint64;
                        mandatory true;
                        description
                          "Group Availability Performance Objective expressed as a percentage.";
                      }
                    }
                  }
                }
              }
            }
          }
        }
      }
    }
    container profiles {
      description
        "Global Profiles.";
      container cos-names {
        description
          "CoS Names (AKA CoS Labels) agreed to between the Service Provider and the Subscribers.";
        list cos-name {
          key "name";
          description
            "List of CoS Names.";
          leaf name {
            type mef-types:identifier45;
            description
              "CoS Name.";
          }
        }
      }
      container bwp-flows-parameter-set {
        description
          "Bandwidth Profile Flows.";
        uses bwp-flows-parameter-set-group;
      }
      container l2cp-cos {
        description
          "Ingress Layer 2 Control Protocol (L2CP) Configuration with CoS Names.";
        list profile {
          key "id";
          description
            "A list of global profiles for Layer 2 Control Processing.";
          reference "[MEF10.3] Section 8.5.";
          container cos-maps {
            description
              "Layer 2 Control Protocol (L2CP) Classes of Service (CoS) Mappings.";
            list cos-map {
              key "protocol protocol-id";
              description
                "The L2CP CoS Map of Protocols to CoS Names.";
              reference "[MEF10.3] Section 8.5. [MEF45] Section 8.1.";
              leaf protocol {
                type mef-types:l2cp-peering-protocol-field-type;
                description
                  "The Protocol is one of Ethertype, LLC, or Other.";
              }
              leaf protocol-id {
                type yang:hex-string;
                description
                  "The Protocol Identifier is the protocol specific value associated with the protocol in a colon separated list of hex values (ie. 88:EE or 82).";
              }
              choice simple-or-subtypes {
                case subtypes-option {
                  container subtypes {
                    presence "subtypes configured";
                    list subtype {
                      key "subtype-id";
                      max-elements "255";
                      leaf subtype-id {
                        type yang:hex-string;
                        description
                          "L2CP Subtype for this Destination MAC's Protocol ID.";
                      }
                      leaf cos-name {
                        type leafref {
                          path "/mef-global:mef-global/profiles/cos-names/cos-name/name";
                        }
                        description
                          "This attribute identifies the name of a class of service (CoS).";
                      }
                    }
                  }
                }
                case simple-option {
                  leaf cos-name {
                    type leafref {
                      path "/mef-global:mef-global/profiles/cos-names/cos-name/name";
                    }
                    description
                      "This attribute identifies the name of a class of service (CoS).";
                  }
                }
              }
            }
          }
          leaf id {
            type mef-types:identifier45;
            description
              "The L2CP ID identifies a specific profile for Layer 2 Control Processing.";
            reference "[MEF10.3] Section 8.5.";
          }
        }
      }
      container l2cp-eec {
        description
          "Egress Layer 2 Control Protocol (L2CP) Configuration with EEC Names.";
        list profile {
          key "id";
          description
            "A list of global profiles for Layer 2 Control Processing.";
          reference "[MEF10.3] Section 8.5.";
          container eec-maps {
            description
              "Layer 2 Control Protocol (L2CP) Profiles or Egress Equivalence Classes.";
            list eec-map {
              key "protocol protocol-id";
              description
                "L2CP Destination MAC Address.";
              reference "[MEF10.3] Section 8.5.";
              leaf protocol {
                type mef-types:l2cp-peering-protocol-field-type;
                description
                  "The Protocol is one of Ethertype, LLC, or Other.";
              }
              leaf protocol-id {
                type yang:hex-string;
                description
                  "The Protocol Identifier is the protocol specific value associated with the protocol in a colon separated list of hex values (ie. 88:EE or 82).";
              }
              choice simple-or-subtypes {
                case subtypes-option {
                  container subtypes {
                    presence "subtypes configured";
                    list subtype {
                      key "subtype-id";
                      max-elements "255";
                      leaf subtype-id {
                        type yang:hex-string;
                        description
                          "L2CP Subtype for this Destination MAC's Protocol ID.";
                      }
                      leaf eec-name {
                        type leafref {
                          path "/mef-global:mef-global/profiles/cos-names/cos-name/name";
                        }
                        description
                          "This attribute identifies the name of a Egress Equivalence Class (EEC).";
                      }
                    }
                  }
                }
                case simple-option {
                  leaf eec-name {
                    type leafref {
                      path "/mef-global:mef-global/profiles/cos-names/cos-name/name";
                    }
                    description
                      "This attribute identifies the name of a Egress Equivalence Class (EEC).";
                  }
                }
              }
            }
          }
          leaf id {
            type mef-types:identifier45;
            description
              "The L2CP ID identifies a specific profile for Layer 2 Control Processing.";
            reference "[MEF10.3] Section 8.5.";
          }
        }
      }
      container l2cp-peering {
        description
          "Layer 2 Control Protocol (L2CP) Configuration for Peering Lists.";
        list profile {
          key "id";
          description
            "A list of global profiles for Layer 2 Control Processing.";
          reference "[MEF10.3] Section 8.5. [MEF45] Section 8.2.";
          container peering-maps {
            description
              "Layer 2 Control Protocol (L2CP) Profiles for Peering.";
            list peering-map {
              key "dest-mac-addr protocol protocol-id";
              description
                "L2CP Destination MAC Address.";
              reference "[MEF10.3] Section 8.5. [MEF45] Section 8.2.";
              leaf dest-mac-addr {
                type yang:mac-address;
                description
                  "The Destination MAC Address for the Layer 2 Control Protocol.";
              }
              leaf protocol {
                type mef-types:l2cp-peering-protocol-field-type;
                description
                  "The Protocol is one of Ethertype, LLC, or Other.";
              }
              leaf protocol-id {
                type yang:hex-string;
                description
                  "The Protocol Identifier is the protocol specific value associated with the protocol in a colon separated list of hex values (ie. 88:EE or 82).";
              }
              leaf-list subtype {
                type yang:hex-string;
                max-elements "255";
                description
                  "L2CP Subtype for this Destination MAC's Protocol ID.";
              }
            }
          }
          leaf id {
            type mef-types:identifier45;
            description
              "The L2CP ID identifies a specific profile for Layer 2 Control Processing.";
            reference "[MEF10.3] Section 8.5.";
          }
        }
      }
      container eec {
        description
          "Egress Equivalence Class (EEC) Profiles.";
        list eec-profile {
          key "id";
          description
            "This attribute identifies the EEC profile";
          reference "[MEF6.2] Appendix A.";
          leaf id {
            type mef-types:identifier45;
            description
              "This attribute identifies the EEC profile.";
          }
          leaf l2cp-eec-id {
            type leafref {
              path "/mef-global:mef-global/profiles/l2cp-eec/profile/id";
            }
            description
              "L2CP Profile Identifier";
          }
          choice eec-id {
            description
              "EEC Identifier.";
            case pcp {
              container eec-pcp {
                presence "EEC Mode PCP.";
                description
                  "EEC Mode PCP.";
                leaf default-pcp-eec-name {
                  type leafref {
                    path "/mef-global:mef-global/profiles/cos-names/cos-name/name";
                  }
                  description
                    "Default value for EEC Name for PCP when it has not been explicitly configured.";
                }
                leaf default-pcp-color {
                  type mef-types:color-type;
                  default "green";
                  description
                    "If the EEC ID = pcp, then this value will be used as the default Color when the PCP value does not have an explicitly configured Color.";
                  reference "MEF 10.3 Section 10.3";
                }
                list pcp {
                  key "pcp-value";
                  description
                    "PCP.";
                  leaf pcp-value {
                    type mef-types:ieee8021p-priority-type;
                    description
                      "Use the VLAN Tag IEEE 802.1p Priority Code Point value (0..7) for CoS.";
                    reference "[MEF10.3] Section 10.2.1.";
                  }
                  leaf discard-value {
                    type boolean;
                    default "false";
                    description
                      "Set to True to discard Service Frames that match to this PCP value.";
                  }
                  leaf eec-name {
                    type leafref {
                      path "/mef-global:mef-global/profiles/cos-names/cos-name/name";
                    }
                    description
                      "This attribute identifies the name of a Egress Equivalence Class instance.";
                  }
                  leaf color {
                    type mef-types:color-type;
                    default "green";
                    description
                      "EVC Per UNI: The EEC Color for Service Frames.";
                    reference "[MEF10.3] [R102], [R103]. ";
                  }
                }
              }
            }
            case dscp {
              container eec-dscp {
                presence "EEC Mode DSCP.";
                description
                  "ECC Mode DSCP.";
                leaf default-ipv4-eec-name {
                  type leafref {
                    path "/mef-global:mef-global/profiles/cos-names/cos-name/name";
                  }
                  description
                    "Default value for EEC Name for DSCP IPv4 Packets when it has not been explicitly configured.";
                }
                leaf default-ipv4-color {
                  type mef-types:color-type;
                  default "green";
                  description
                    "If the EEC ID = dscp, then this value will be used as the default Color when the DSCP value for IPv4 does not have an explicitly configured Color.";
                  reference "MEF 10.3 Section 10.3";
                }
                leaf default-ipv6-eec-name {
                  type leafref {
                    path "/mef-global:mef-global/profiles/cos-names/cos-name/name";
                  }
                  description
                    "Default value for EEC Name for DSCP IPv6 Packets when it has not been explicitly configured.";
                }
                leaf default-ipv6-color {
                  type mef-types:color-type;
                  default "green";
                  description
                    "If the EEC ID = dscp, then this value will be used as the default Color when the DSCP value for IPv6 does not have an explicitly configured Color.";
                  reference "MEF 10.3 Section 10.3";
                }
                list ipv4-dscp {
                  key "dscp-value";
                  description
                    "DSCP value for IPv4 Packets.";
                  leaf dscp-value {
                    type inet:dscp;
                    description
                      "Map CoS to IPv4 DSCP values.";
                  }
                  leaf discard-value {
                    type boolean;
                    default "false";
                    description
                      "Set to True to discard Service Frames that match to this DSCP value.";
                  }
                  leaf eec-name {
                    type leafref {
                      path "/mef-global:mef-global/profiles/cos-names/cos-name/name";
                    }
                    description
                      "This attribute identifies the name of a Egress Equivalence Class instance.";
                  }
                  leaf color {
                    type mef-types:color-type;
                    default "green";
                    description
                      "EVC Per UNI: The EEC Color for Service Frames.";
                    reference "[MEF10.3] [R102], [R103]. ";
                  }
                }
                list ipv6-dscp {
                  key "dscp-value";
                  description
                    "DSCP value for IPv6 Packets.";
                  leaf dscp-value {
                    type inet:dscp;
                    description
                      "Map EEC to IPv4 and IPv6 DSCP values.";
                  }
                  leaf discard-value {
                    type boolean;
                    default "false";
                    description
                      "Set to True to discard Service Frames that match to this DSCP value.";
                  }
                  leaf eec-name {
                    type leafref {
                      path "/mef-global:mef-global/profiles/cos-names/cos-name/name";
                    }
                    description
                      "This attribute identifies the name of a Egress Equivalence Class instance.";
                  }
                  leaf color {
                    type mef-types:color-type;
                    default "green";
                    description
                      "EVC Per UNI: The EEC Color for Service Frames.";
                    reference "[MEF10.3] [R102], [R103]. ";
                  }
                }
              }
            }
          }
        }
      }
      container cos {
        description
          "Class of Service (CoS) Profiles.";
        list cos-profile {
          key "id";
          description
            "This attribute identifies the identifier of a Class of Service (CoS) instance.";
          reference "[MEF6.2] Appendix A.";
          leaf id {
            type mef-types:identifier45;
            description
              "This attribute identifies the label of a Class of Service (CoS) instance.";
          }
          leaf l2cp-cos-id {
            type leafref {
              path "/mef-global:mef-global/profiles/l2cp-cos/profile/id";
            }
            description
              "L2CP Profile Identifier";
          }
          choice cos-id {
            description
              "CoS identifier.";
            case evc {
              container cos-evc {
                presence "EVC ID PCP.";
                description
                  "CoS ID EVC.";
                leaf default-evc-cos-name {
                  type leafref {
                    path "/mef-global:mef-global/profiles/cos-names/cos-name/name";
                  }
                  description
                    "This attribute identifies the name of a Class of Service (CoS) instance.";
                }
                leaf default-evc-color {
                  type mef-types:color-type;
                  default "green";
                  description
                    "If the CoS ID = evc, then all service frames are treated with the same color.";
                  reference "MEF 10.3 Section 10.3";
                }
              }
            }
            case pcp {
              container cos-pcp {
                presence "CoS ID PCP.";
                description
                  "CoS ID PCP.";
                leaf default-pcp-cos-name {
                  type leafref {
                    path "/mef-global:mef-global/profiles/cos-names/cos-name/name";
                  }
                  description
                    "Default value for CoS Name for PCP when it has not been explicitly configured.";
                }
                leaf default-pcp-color {
                  type mef-types:color-type;
                  default "green";
                  description
                    "If the CoS ID = pcp, then this value will be used as the default Color when the PCP value does not have an explicitly configured Color.";
                  reference "MEF 10.3 Section 10.3";
                }
                list pcp {
                  key "pcp-value";
                  description
                    "PCP.";
                  leaf pcp-value {
                    type mef-types:ieee8021p-priority-type;
                    description
                      "Use the VLAN Tag IEEE 802.1p Priority Code Point value (0..7) for CoS.";
                  }
                  leaf discard-value {
                    type boolean;
                    default "false";
                    description
                      "Set to True to discard Service Frames that match to this PCP value.";
                  }
                  leaf cos-name {
                    type leafref {
                      path "/mef-global:mef-global/profiles/cos-names/cos-name/name";
                    }
                    description
                      "This attribute identifies the name of a class of service (CoS) instance.";
                  }
                  leaf color {
                    type mef-types:color-type;
                    default "green";
                    description
                      "EVC Per UNI: The CoS Color for Service Frames.";
                    reference "[MEF10.3] [R102], [R103]. ";
                  }
                }
              }
            }
            case dscp {
              container cos-dscp {
                presence "CoS ID DSCP.";
                description
                  "CoS ID DSCP.";
                leaf default-ipv4-cos-name {
                  type leafref {
                    path "/mef-global:mef-global/profiles/cos-names/cos-name/name";
                  }
                  description
                    "Default value for CoS Name for DSCP IPv4 Packets when it has not been explicitly configured.";
                }
                leaf default-ipv4-color {
                  type mef-types:color-type;
                  default "green";
                  description
                    "If the CoS ID = dscp, then this value will be used as the default Color when the DSCP value for IPv4 does not have an explicitly configured Color.";
                  reference "MEF 10.3 Section 10.3";
                }
                leaf default-ipv6-cos-name {
                  type leafref {
                    path "/mef-global:mef-global/profiles/cos-names/cos-name/name";
                  }
                  description
                    "Default value for CoS Name for DSCP IPv6 Packets when it has not been explicitly configured.";
                }
                leaf default-ipv6-color {
                  type mef-types:color-type;
                  default "green";
                  description
                    "If the CoS ID = dscp, then this value will be used as the default Color when the DSCP value for IPv6 does not have an explicitly configured Color.";
                  reference "MEF 10.3 Section 10.3";
                }
                list ipv4-dscp {
                  key "dscp-value";
                  description
                    "DSCP value for IPv4 Packets.";
                  leaf dscp-value {
                    type inet:dscp;
                    description
                      "Map CoS to IPv4 and IPv6 DSCP values.";
                  }
                  leaf discard-value {
                    type boolean;
                    default "false";
                    description
                      "Set to True to discard Service Frames that match to this DSCP value.";
                  }
                  leaf cos-name {
                    type leafref {
                      path "/mef-global:mef-global/profiles/cos-names/cos-name/name";
                    }
                    description
                      "This attribute identifies the name of a Class of Service (CoS) instance.";
                  }
                  leaf color {
                    type mef-types:color-type;
                    default "green";
                    description
                      "EVC Per UNI: The CoS Color for Service Frames.";
                    reference "[MEF10.3] [R102], [R103]. ";
                  }
                }
                list ipv6-dscp {
                  key "dscp-value";
                  description
                    "DSCP value for IPv6 Packets.";
                  leaf dscp-value {
                    type inet:dscp;
                    description
                      "Map CoS to IPv4 and IPv6 DSCP values.";
                  }
                  leaf discard-value {
                    type boolean;
                    default "false";
                    description
                      "Set to True to discard Service Frames that match to this DSCP value.";
                  }
                  leaf cos-name {
                    type leafref {
                      path "/mef-global:mef-global/profiles/cos-names/cos-name/name";
                    }
                    description
                      "This attribute identifies the name of a Class of Service (CoS) instance.";
                  }
                  leaf color {
                    type mef-types:color-type;
                    default "green";
                    description
                      "EVC Per UNI: The CoS Color for Service Frames.";
                    reference "[MEF10.3] [R102], [R103]. ";
                  }
                }
              }
            }
          }
        }
      }
    }
  }
}
