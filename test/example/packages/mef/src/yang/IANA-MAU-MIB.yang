/*
 * Generated by ncsc --mib2yang
 * Source: IANA-MAU-MIB.mib
 */
module IANA-MAU-MIB {
  namespace "http://tail-f.com/ns/mibs/IANA-MAU-MIB/200704210000Z";
  prefix IANA_MAU_MIB;
  tailf:id "";
  tailf:snmp-mib-module-name "IANA-MAU-MIB";
  import tailf-common {
    prefix tailf;
  }

  revision 2007-04-21 {
    description
      "";
  }

  typedef IANAifMauTypeListBits {
    type bits {
      bit bOther {
        position 0;
      }
      bit bAUI {
        position 1;
      }
      bit b10base5 {
        position 2;
      }
      bit bFoirl {
        position 3;
      }
      bit b10base2 {
        position 4;
      }
      bit b10baseT {
        position 5;
      }
      bit b10baseFP {
        position 6;
      }
      bit b10baseFB {
        position 7;
      }
      bit b10baseFL {
        position 8;
      }
      bit b10broad36 {
        position 9;
      }
      bit b10baseTHD {
        position 10;
      }
      bit b10baseTFD {
        position 11;
      }
      bit b10baseFLHD {
        position 12;
      }
      bit b10baseFLFD {
        position 13;
      }
      bit b100baseT4 {
        position 14;
      }
      bit b100baseTXHD {
        position 15;
      }
      bit b100baseTXFD {
        position 16;
      }
      bit b100baseFXHD {
        position 17;
      }
      bit b100baseFXFD {
        position 18;
      }
      bit b100baseT2HD {
        position 19;
      }
      bit b100baseT2FD {
        position 20;
      }
      bit b1000baseXHD {
        position 21;
      }
      bit b1000baseXFD {
        position 22;
      }
      bit b1000baseLXHD {
        position 23;
      }
      bit b1000baseLXFD {
        position 24;
      }
      bit b1000baseSXHD {
        position 25;
      }
      bit b1000baseSXFD {
        position 26;
      }
      bit b1000baseCXHD {
        position 27;
      }
      bit b1000baseCXFD {
        position 28;
      }
      bit b1000baseTHD {
        position 29;
      }
      bit b1000baseTFD {
        position 30;
      }
      bit b10GbaseX {
        position 31;
      }
      bit b10GbaseLX4 {
        position 32;
      }
      bit b10GbaseR {
        position 33;
      }
      bit b10GbaseER {
        position 34;
      }
      bit b10GbaseLR {
        position 35;
      }
      bit b10GbaseSR {
        position 36;
      }
      bit b10GbaseW {
        position 37;
      }
      bit b10GbaseEW {
        position 38;
      }
      bit b10GbaseLW {
        position 39;
      }
      bit b10GbaseSW {
        position 40;
      }
      bit b10GbaseCX4 {
        position 41;
      }
      bit b2BaseTL {
        position 42;
      }
      bit b10PassTS {
        position 43;
      }
      bit b100BaseBX10D {
        position 44;
      }
      bit b100BaseBX10U {
        position 45;
      }
      bit b100BaseLX10 {
        position 46;
      }
      bit b1000BaseBX10D {
        position 47;
      }
      bit b1000BaseBX10U {
        position 48;
      }
      bit b1000BaseLX10 {
        position 49;
      }
      bit b1000BasePX10D {
        position 50;
      }
      bit b1000BasePX10U {
        position 51;
      }
      bit b1000BasePX20D {
        position 52;
      }
      bit b1000BasePX20U {
        position 53;
      }
    }
  }

  typedef IANAifMauMediaAvailable {
    type enumeration {
      enum "other" {
        value 1;
      }
      enum "unknown" {
        value 2;
      }
      enum "available" {
        value 3;
      }
      enum "notAvailable" {
        value 4;
      }
      enum "remoteFault" {
        value 5;
      }
      enum "invalidSignal" {
        value 6;
      }
      enum "remoteJabber" {
        value 7;
      }
      enum "remoteLinkLoss" {
        value 8;
      }
      enum "remoteTest" {
        value 9;
      }
      enum "offline" {
        value 10;
      }
      enum "autoNegError" {
        value 11;
      }
      enum "pmdLinkFault" {
        value 12;
      }
      enum "wisFrameLoss" {
        value 13;
      }
      enum "wisSignalLoss" {
        value 14;
      }
      enum "pcsLinkFault" {
        value 15;
      }
      enum "excessiveBER" {
        value 16;
      }
      enum "dxsLinkFault" {
        value 17;
      }
      enum "pxsLinkFault" {
        value 18;
      }
      enum "availableReduced" {
        value 19;
      }
      enum "ready" {
        value 20;
      }
    }
  }

  typedef IANAifMauAutoNegCapBits {
    type bits {
      bit bOther {
        position 0;
      }
      bit b10baseT {
        position 1;
      }
      bit b10baseTFD {
        position 2;
      }
      bit b100baseT4 {
        position 3;
      }
      bit b100baseTX {
        position 4;
      }
      bit b100baseTXFD {
        position 5;
      }
      bit b100baseT2 {
        position 6;
      }
      bit b100baseT2FD {
        position 7;
      }
      bit bFdxPause {
        position 8;
      }
      bit bFdxAPause {
        position 9;
      }
      bit bFdxSPause {
        position 10;
      }
      bit bFdxBPause {
        position 11;
      }
      bit b1000baseX {
        position 12;
      }
      bit b1000baseXFD {
        position 13;
      }
      bit b1000baseT {
        position 14;
      }
      bit b1000baseTFD {
        position 15;
      }
    }
  }

  typedef IANAifJackType {
    type enumeration {
      enum "other" {
        value 1;
      }
      enum "rj45" {
        value 2;
      }
      enum "rj45S" {
        value 3;
      }
      enum "db9" {
        value 4;
      }
      enum "bnc" {
        value 5;
      }
      enum "fAUI" {
        value 6;
      }
      enum "mAUI" {
        value 7;
      }
      enum "fiberSC" {
        value 8;
      }
      enum "fiberMIC" {
        value 9;
      }
      enum "fiberST" {
        value 10;
      }
      enum "telco" {
        value 11;
      }
      enum "mtrj" {
        value 12;
      }
      enum "hssdc" {
        value 13;
      }
      enum "fiberLC" {
        value 14;
      }
      enum "cx4" {
        value 15;
      }
    }
  }
}
